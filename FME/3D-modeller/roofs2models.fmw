FME workspace roofs2models.fmw

Parameters:
- SourceDataset_GEOTIFF = $(FME_MF_DIR)MARKMODELL\01m\GEOTIFF\*.tif   # Source GeoTIFF File(s) or URL(s)
- DestDataset_CITYGML = $(FME_MF_DIR)BYGGNADSMODELL\01m\CityGMLByggnader.gml   # Destination CityGML Document
- DestDataset_CITYJSON = $(FME_MF_DIR)BYGGNADSMODELL\01m\CityJSONBYggnaderTyreso.json   # Destination CityJSON File
- SourceDataset_ACAD_3 = C:\Users\SEIAMM\Documents\tyresö\3D-byggnader\Tyresö_3D_byggnader_2015_shape.DWG   # Source Autodesk AutoCAD DWG/DXF File(s)
- FEATURE_TYPES =

Readers:
- ACAD_2: ACAD from $(SourceDataset_ACAD_3) in EPSG:3011
- GEOTIFF_1: GEOTIFF from $(SourceDataset_GEOTIFF) in EPSG:3011

Writers:
- CITYGML_1: CITYGML to $(DestDataset_CITYGML) in EPSG:3011
- CITYJSON_1: CITYJSON to $(DestDataset_CITYJSON)

0 (reader ACAD_2)
    -> Generalizer_2
    -> Densifier
Building (writer CITYJSON_1) [off]
    attributes: fid string, class string, creationDate string, function string, terminationDate string, usage string, geographicalExtent{} real64, address.CountryName string, address.LocalityName string, address.PostalCode string, address.ThoroughfareName string, address.ThoroughfareNumber string, address.location.boundaries{} int32, address.location.lod real64, measuredHeight real64, roofType string, storeyHeightsAboveGround{} real64, storeyHeightsBelowGround{} real64, storeysAboveGround int32, storeysBelowGround int32, yearOfConstruction int32, yearOfDemolition int32

Bookmark: Skapar volymer. volym som börjar från minsta höjdpunkt från terräng till tak och en volym från tak ned mot terräng
Generalizer_2
    ALG = Douglas
    CLEANING_TOLERANCE_LOOKUP = AUTO
    GROUP_BY = autocad_entity_handle
    PRESERVE = Yes
    PRESERVE_PATHS_LOOKUP = YES
    TOLERANCE = 0.05
    ALG_TEXT = Douglas (Generalize)
    CLEANING_TOLERANCE = Automatic
    PRESERVE_PATHS = Yes
    -> Extruder
Extruder
    DIRECTION_LOOKUP = SPECIFIED
    EXTRUSION_X = 0.0
    EXTRUSION_Y = 0.0
    EXTRUSION_Z = -200
    DIRECTION = Specified
    EXTRUDED -> CSGBuilder [A]
LineBuilder
    ACCUM_INPUT_ATTRS_LOOKUP = One
    GROUP_BY = autocad_entity_handle
    REMOVE_DUPLICATES_LOOKUP = NO
    ACCUM_INPUT_ATTRS = Use Attributes From One Feature
    REMOVE_DUPLICATES = No
    POLYGON -> Generalizer
Generalizer
    ALG = Douglas
    CLEANING_TOLERANCE_LOOKUP = AUTO
    GROUP_BY = autocad_entity_handle
    PRESERVE = Yes
    PRESERVE_PATHS_LOOKUP = YES
    TOLERANCE = 0.05
    ALG_TEXT = Douglas (Generalize)
    CLEANING_TOLERANCE = Automatic
    PRESERVE_PATHS = Yes
    -> Extruder_4
Extruder_4
    DIRECTION_LOOKUP = SPECIFIED
    EXTRUSION_X = 0.0
    EXTRUSION_Y = 0.0
    EXTRUSION_Z = 200
    DIRECTION = Specified
    EXTRUDED -> CSGBuilder [B]

Bookmark: Tar ut vertex av takkonturen
Densifier
    INTERVAL = 1
    MODE_LOOKUP = xy_uniform
    MODE = Uniform Interval
    DENSIFIED -> VertexExtractor
VertexExtractor
    Point -> PointOnRasterValueExtractor [POINT]

Bookmark: Läser in och bygger ihop raster
GEOTIFF (reader GEOTIFF_1)
    -> RasterMosaicker
RasterMosaicker
    ACCUM_ATTRS = ONE
    INTERPOLATION_TYPE = NearestNeighbor
    MERGE_PALETTES_NAME = Yes
    NODATA_OVERWRITE = No
    OVERLAPPING_VALUES = last
    SNAPPING_TYPE = RESAMPLE
    ACCUM_ATTRS_NAME = Use Attributes From One Feature
    INTERPOLATION_TYPE_NAME = Nearest Neighbor
    MERGE_PALETTES = Yes
    SNAPPING_TYPE_NAME = Resample
    -> PointOnRasterValueExtractor [RASTER]

Bookmark: Tar ut höjd data från raster för vardera vertex. Tar sedan det misnta värdet och sätter det för varde tak-grupp som Z.
PointOnRasterValueExtractor
    INTERPOLATION_TYPE = NearestNeighbor
    INTERPOLATION_TYPE_NAME = Nearest Neighbor
    POINT -> StatisticsCalculator_2
StatisticsCalculator_2
    ATTR_ACCUM_MODE = None
    CALCULATION_MODE = NUMERIC
    FEAT_STATS = _band{0}.value,NUMERIC_MODE,MIN,,,,,,,,,,,,
    GROUP_BY = autocad_entity_handle
    COMPLETE -> 3DForcer_3
3DForcer_3
    KEEPZVAL = No
    ZVALATTR = @Value(_band{0}.value.min)
    -> LineBuilder

Bookmark: Clipper båda volymer för att få volymen som överlappar varan
CSGBuilder
    ATTR_CONFLICT_RES_LOOKUP = A_IF_CONFLICT
    GROUP_BY = autocad_entity_handle
    ATTR_ACCUM_MODE = Merge
    ATTR_CONFLICT_RES = Use A
    INTERSECTION -> Building (writer CITYJSON_1)
    INTERSECTION -> AttributeCreator

Bookmark: Spara som CITYGML och upprätta CITYGML attribut
AttributeCreator
    ATTR_TABLE = SET_TO citygml_lod_name (varchar(9)) = lod2Solid
    -> GeometryPropertySetter
GeometryPropertySetter
    DO_REMOVE_ATTR = NOT_THIS_TIME
    OVERWRITE_CHOICE_OPT = yes
    SETTYPE_PARAM = Traits From Attributes
    SRC_ATTRS = citygml_lod_name
    OVERWRITE_CHOICE = Yes
    REMOVE_ATTRIBUTE = No
    SET -> AttributeRemover
AttributeRemover
    REMOVE_ATTRS = _band{0}.value.min,_band{0}.palette{0}.value,_band{0}.value,_feature_number,_part_number,_vertex_number,_x,_y,_z,fme_basename
    -> Building (writer CITYGML_1)
Building (writer CITYGML_1)
    attributes: autocad_entity_handle xml_char(50), _band{}.value xml_real64, _band{}.palette{}.value xml_real64
