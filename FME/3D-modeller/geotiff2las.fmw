FME workspace geotiff2las.fmw

Parameters:
- SourceDataset_GEOTIFF = ""$(FME_MF_DIR)BYGGNADSMODELL\01m\GEOTIFF\*.tif" "$(FME_MF_DIR)BYGGNADSMODELL\01m\GEOTIFF\*.tiff" "$(FME_MF_DIR)BYGGNADSMODELL\01m\GEOTIFF\*.itiff" "$(FME_MF_DIR)BYGGNADSMODELL\01m\GEOTIFF\*.ovr""   # Source GeoTIFF File(s) or URL(s)
- DestDataset_LAS = $(FME_MF_DIR)BYGGNADSMODELL\01m\LAS   # Destination ASPRS LAS Folder

Readers:
- GEOTIFF_1: GEOTIFF from $(SourceDataset_GEOTIFF) in EPSG:3011

Writers:
- LAS_1: LAS to $(DestDataset_LAS)

GEOTIFF (reader GEOTIFF_1)
    -> Reprojector
Reprojector
    DEST = EPSG:4326
    INTERPOLATION_TYPE = ,NearestNeighbor
    RASTER_CELL_SIZE_LOOKUP = ,PreserveCells
    RASTER_TOLERANCE = 0.0
    SOURCE = EPSG:3011
    INTERPOLATION_TYPE_NAME = Nearest Neighbor
    RASTER_CELL_SIZE = Preserve Cells
    REPROJECTED -> RasterCellCoercer
RasterCellCoercer
    CELL_GEOMETRY = Points
    EXTRACT_NODATA = No
    EXTRACT_VALUES_AS_ATTRIBUTES = No
    PRESERVE_ATT = YES
    CELL_GEOMETRY_LOOKUP = Points
    EXTRACT_BAND_VALUES_AS = Z Values
    EXTRACT_NODATA_LOOKUP = No
    PRESERVE_ATTRIBUTES = Yes
    -> PointCloudCombiner
PointCloudCombiner
    ACCUM_ATTRS = yes
    EXTRACT_RASTER_NODATA = no
    SPACING = 1.0
    ACCUM_ATTRS_NAME = Yes
    EXTRACT_RASTER_NODATA_NAME = No
    -> File1 (writer LAS_1)
File1 (writer LAS_1)
