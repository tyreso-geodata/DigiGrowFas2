FME workspace ASCII2GEOTIFF.fmw

Parameters:
- SourceDataset_ESRIASCIIGRID = ""$(FME_MF_DIR)MARKMODELL\01m\ASCII\*.asc" "$(FME_MF_DIR)MARKMODELL\01m\ASCII\*.grd""   # Source Esri ASCII Grid File(s)
- DestDataset_GEOTIFF = $(FME_MF_DIR)MARKMODELL\01m\GEOTIFF   # Destination GeoTIFF Folder

Readers:
- ESRIASCIIGRID_1: ESRIASCIIGRID from $(SourceDataset_ESRIASCIIGRID) in EPSG:3011

Writers:
- GEOTIFF_1: GEOTIFF to $(DestDataset_GEOTIFF) in EPSG:3011

ESRIASCIIGRID (reader ESRIASCIIGRID_1)
    -> Raster1 (writer GEOTIFF_1)
Raster1 (writer GEOTIFF_1)
