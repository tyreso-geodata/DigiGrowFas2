FME workspace dynamic_parameters.fmw

Parameters:
- DestDataset_JSON = $(FME_MF_DIR)test.json   # Enter Text Data

Writers:
- TEXTLINE_1: TEXTLINE to C:\Users\SEIAMM\Downloads\test.json

Creator
    GEOMTYPE = Geometry Object
    NUM = 1
    CREATED -> SQLExecutor [INITIATOR]
    CREATED -> SQLExecutor_2 [INITIATOR]

Bookmark: Hämta Projektnamn
SQLExecutor
    COMBINE_ATTRS = Result Attributes Only
    COMBINE_GEOM = Result Geometry Only
    DATASET = dg_verksamhetsdata
    FORMAT = POSTGIS
    INPUT_PORT_INITIATOR_CONNECTED = CONNECTED
    OUTPUT_FEATURES = DATA_ONLY
    POSTGIS_CREATE_FEATURE_TABLES_FROM_DATA = Yes
    POSTGIS_DISABLE_COLLECTION_SPLITTING = yes
    POSTGIS_HOST = 172.23.0.154
    POSTGIS_PASSWORD =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
    POSTGIS_PORT = 5432
    POSTGIS_QUERY_FEATURE_TYPES_FOR_MERGE_FILTERS = Yes
    POSTGIS_READ_TIME_WITH_TIMEZONE = Yes
    POSTGIS_SCHEMAS_FOR_TABLE_LISTING = lageryta
    POSTGIS_SSLMODE = prefer
    POSTGIS_USER_NAME = Sweco
    POSTGIS_USE_TRUE_POSTGIS_TYPES = yes
    SQL_STATEMENT:
      SELECT
        json_build_object(
          'name', 'PROJEKTNAMN',
          'defaultValue', '',
          'choices', COALESCE(
            (
              SELECT json_agg(
                json_build_object(
                  'display', f.name,
                  'value', f.name <pipe><pipe> ' - ' <pipe><pipe> f.projekt_nr
                )
                ORDER BY f.id
              )
              FROM analys.projekt_y f
              WHERE f.name IS NOT NULL
            ),
            '[]'::json
          )
        ) AS result;
    RESULT -> AttributeExposer
AttributeExposer
    ATTR_TABLE = result,json
    -> JSONUpdater [DOCUMENT]

Bookmark: Hämtar geometrier för handlingar
SQLExecutor_2
    COMBINE_ATTRS = Result Attributes Only
    COMBINE_GEOM = Result Geometry Only
    DATASET = relationshandlingar
    FORMAT = POSTGIS
    INPUT_PORT_INITIATOR_CONNECTED = CONNECTED
    OUTPUT_FEATURES = DATA_ONLY
    POSTGIS_CREATE_FEATURE_TABLES_FROM_DATA = Yes
    POSTGIS_DISABLE_COLLECTION_SPLITTING = yes
    POSTGIS_HOST = 172.23.0.154
    POSTGIS_PASSWORD =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
    POSTGIS_PORT = 5432
    POSTGIS_QUERY_FEATURE_TYPES_FOR_MERGE_FILTERS = Yes
    POSTGIS_READ_TIME_WITH_TIMEZONE = Yes
    POSTGIS_SCHEMAS_FOR_TABLE_LISTING = lageryta
    POSTGIS_SSLMODE = prefer
    POSTGIS_USER_NAME = fme_user
    POSTGIS_USE_TRUE_POSTGIS_TYPES = yes
    SQL_STATEMENT:
      SELECT
        json_build_object(
          'name', 'GEOMETRY_LIST',
          'defaultValue', '',
          'choices', COALESCE(
            (
              SELECT json_agg(
                json_build_object(
                  'display', p.projektnamn <pipe><pipe> ' - ' <pipe><pipe> f.filnamn,
                  'value', ST_AsText(f.projektomrade)
                )
              )
              FROM lageryta.filer f
              JOIN lageryta.projekt p ON f.projekt_id = p.id
              WHERE f.projektomrade IS NOT NULL
            ),
            '[]'::json
          )
        ) AS result;
    RESULT -> AttributeExposer_2
AttributeExposer_2
    ATTR_TABLE = result,json
    -> StringReplacer
StringReplacer
    CASE = NO
    NO_MATCH = _FME_NO_OP_
    REGEXP = NO
    STR_REPLACE_TABLE = "result \\\" "
    -> JSONUpdater [UPDATE]

Bookmark: Bygga JSON
Note: Tar DOCUMENT från första queryn och APPEND_TO_ARRAY från andra queryn. Skriver ut slutlig JSON till fil (Text Line)
JSONUpdater
    INPUT_PORT_DOCUMENT_CONNECTED = CONNECTED
    INPUT_PORT_UPDATE_CONNECTED = CONNECTED
    JSON_TEXT = [@Value(result)]
    JSON_TYPE = Text or Attribute
    QUERY_VALIDATE = YES
    RESULT_ATTRIBUTE = _result
    UPDATE_TABLE = GENERATE_JSON_QUERY APPEND_TO_ARRAY json <Unused> JSON @Value(result)
    VISIBLE_QUERY_VALIDATE = Yes
    DOCUMENT -> text_line (writer TEXTLINE_1)
text_line (writer TEXTLINE_1)
    attributes: text_line_data buffer
