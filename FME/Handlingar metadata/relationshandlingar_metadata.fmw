FME workspace relationshandlingar_metadata.fmw

Parameters:
- GLB =   # Parameter Group
- WORKSPACE = $(FME_MF_DIR)dwg2view.fmw   # workspace
- ROTMAP = E:\Relationshandlingar
- GROUP_1 =   # PYTHON
- GLTFPACK = $(FME_MF_DIR_USERTYPED)gltfpack-windows\gltfpack.exe
- IFCCONVERT = $(FME_MF_DIR_USERTYPED)ifcconvert-0.8.4-win64\IfcConvert.exe
- PROJINFO =   # Projektinformation
- PROJEKTNAMN = Bollmoravägen - 225   # "test,Bollmoravägen - 225" Projektnamn
- LEX_DIARIENUMMER = test4488912   # LEX diarienummer
- GEO_INFO =   # Geografisk information
- MESSAGE_1 =
- GEOMETRY_LIST = POLYGON((18.337727 59.22858, 18.34116 59.227965, 18.342361 59.229019, 18.341761 59.230292, 18.339272 59.231039, 18.336697 59.230819, 18.327427 59.228931, 18.327599 59.225725, 18.327942 59.224057, 18.333693 59.222519, 18.337812 59.221114, 18.350773 59.219972, 18.357983 59.220104, 18.363905 59.222871, 18.359356 59.223222, 18.356094 59.222256, 18.350601 59.221948, 18.345194 59.221904, 18.342447 59.222036, 18.337383 59.222651, 18.334723 59.223749, 18.332577 59.224584, 18.330259 59.225462, 18.33292 59.22555, 18.337727 59.22858))
- GEOMETRY = ej vald   # Eller rita utsträckning (om område från befintlig relationshandling är valt, skriv "ej vald")
- FILINFO =   # Filinformation
- FASTIGHETSBETECKNING = hh5   # Fastighetsbeteckning
- SOURCE_FILE = \\tsclient\Guacamole Filesystem\L-30-P-001.dwg   # "" Fil
- TEK_KLASS =   # Teknisk klassificering
- DISCIPLIN = Arkitektur   # Disciplin
- OBJEKTTYP = samhällsfastigheter   # Samhällsfastigheter ,samhällsfastigheter%Infrastruktur,infrastruktur Objekttyp
- DOKHANT =   # UPPRATTAD_AV Dokumenthantering
- UPPRATTAD_AV = test   # Upprättad av (Företag eller Tyresö kommun)
- SOKBARHET =   # Sökbarhet
- MESSAGE_2 =
- TAGGAR = tagg1,tagg2,tagg3   # Taggar: tagg1,tagg2,tagg3

Writers:
- FILECOPY_1: FILECOPY to $(ROTMAP)\$(PROJEKTNAMN)

Tester_3
    BOOL_OP = OR
    TEST_CLAUSE = TEST @Value(FILTYP) = ifc
    TEST_MODE = TEST
    PASSED -> PythonCaller_3
    FAILED -> WorkspaceRunner
    FAILED -> FMEFlowJobSubmitter

Bookmark: New Bookmark
Note: Läser $(SOURCE_FILE), tolkar ev. flera filer, bygger listan source_files{}.path och exploderar till en feature per fil.
Creator
    GEOMTYPE = Geometry Object
    NUM = 1
    CREATED -> PythonCaller_8
PythonCaller_8
    INPUT_PORT_CONNECTED = CONNECTED
    PYTHONSOURCE:
      import re
      import fme
      from fme import BaseTransformer
      import fmeobjects

      class FeatureProcessor(BaseTransformer):
          def input(self, feature: fmeobjects.FMEFeature):
              raw = fme.macroValues.get('SOURCE_FILE', '')
              raw = str(raw).strip()

              # Multi-file case: "c:\a.dwg","c:\b.dwg"
              paths = [p.strip() for p in re.findall(r'"([^"]+)"', raw) if p.strip()]

              # Single-file case: c:\a.ifc  (no quotes)
              if not paths and raw:
                  paths = [raw]

              for i, p in enumerate(paths):
                  feature.setAttribute(f"source_files{{{i}}}.path", p)

              feature.setAttribute("source_files_count", len(paths))
              self.pyoutput(feature)
    PYTHONSYMBOL = FeatureProcessor
    -> AttributeExposer_3
AttributeExposer_3
    ATTR_TABLE = source_files{}.path,
    -> ListExploder
ListExploder
    ATTR_CONFLICT_RES_LOOKUP = INCOMING_IF_CONFLICT
    INDEX_ATTR = _element_index
    LIST_ATTR = source_files{}
    ATTR_ACCUM_MODE = Merge List Attributes
    ATTR_CONFLICT_RES = Use List Attribute Values
    ELEMENTS -> Tester

Bookmark: New Bookmark
Tester
    BOOL_OP = OR
    TEST_CLAUSE = CASE_INSENSITIVE_TEST $(GEOMETRY) CONTAINS "type":"
    TEST_MODE = CASE_INSENSITIVE_TEST
    PASSED -> GeometryReplacer
    FAILED -> GeometryReplacer_2
GeometryReplacer
    KIND = GEOJSON
    REMOVE_ATTRIBUTE = Yes
    SOURCE = $(GEOMETRY)
    KIND_LONG = GeoJSON
    -> GeometryExtractor
GeometryReplacer_2
    KIND = wkt
    OGC_WKT_PRECISION = FLOAT_64
    REMOVE_ATTRIBUTE = Yes
    SOURCE = $(GEOMETRY_LIST)
    KIND_LONG = OGC Well Known Text
    OGC_WKT_PRECISION_DISPLAY = 64-bit
    -> GeometryExtractor
Note: Tar fram FILTYP (dwg/ifc/invalid), filstorlek och projektnamn/id. Bygger SAVE_PATH/PROJECT_MAP. Tester_4 stoppar invalid.
GeometryExtractor
    ATTR = _geometry
    KIND = wkt
    OGCVERSION = 1.2
    OGC_WKT_PRECISION = FLOAT_64
    REMOVE_GEOMETRY = No
    KIND_LONG = OGC Well Known Text
    OGC_WKT_PRECISION_DISPLAY = 64-bit
    -> PythonCaller_7
PythonCaller_7
    INPUT_PORT_CONNECTED = CONNECTED
    PYTHONSOURCE:
      import fme
      from fme import BaseTransformer
      import fmeobjects
      import os


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""

              # Get the source file path from FME macro values
              source_file = fme.macroValues.get('SOURCE_FILE', '')

              if source_file and os.path.exists(source_file):
                  # Get file size in bytes
                  file_size = os.path.getsize(source_file)
                  feature.setAttribute('file_size_bytes', file_size)

                  # Optional: also set file size in MB for convenience
                  file_size_mb = file_size / (1024 * 1024)
                  feature.setAttribute('file_size_mb', round(file_size_mb, 2))
              else:
                  # Handle case where file doesn't exist or macro is empty
                  feature.setAttribute('file_size_bytes', -1)
                  feature.setAttribute('file_size_mb', -1)

              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> AttributeExposer_2
AttributeExposer_2
    ATTR_TABLE = file_size_mb,,file_size_bytes,
    -> AttributeCreator_4
AttributeCreator_4
    ATTR_TABLE:
      SET_TO $(FASTIGHETSBETECKNING) (varchar(200))
      SET_TO $(DISCIPLIN) (varchar(200))
      SET_TO $(OBJEKTTYP) (varchar(200))
      SET_TO $(UPPRATTAD_AV) (varchar(200))
      SET_TO $(TAGGAR) (varchar(200))
      SET_TO $(SOURCE_FILE) (varchar(200))
      SET_TO IfcConvert (varchar(200)) = $(IFCCONVERT)
      SET_TO gltfpack (varchar(200)) = $(GLTFPACK)
      SET_TO FILTYP (varchar(200)) = FME_CONDITIONAL:DEFAULT_VALUE'invalid'BOOL_OP;OR;COMPOSITE_TEST;1;CASE_INSENSITIVE_TEST @Value(path) CONTAINS .dwg'dwg'BOOL_OP;OR;COMPOSITE_TEST;1;CASE_INSENSITIVE_TEST @Value(path) CONTAINS .ifc'ifc'FME_NUM_CONDITIONS3___
      SET_TO FILSTORLEK (uint64) = @Value(file_size_bytes)
      SET_TO FILNAMN (varchar(200)) = @ReplaceRegularExpression(@ReplaceRegularExpression(@Value(path),"^.*[/\\]","",caseSensitive=TRUE),"\.\w+$","",caseSensitive=TRUE)
      SET_TO PROJEKTNAMN (varchar(200)) = $(PROJEKTNAMN)
    INPUT_PORT_CONNECTED = CONNECTED
    -> AttributeCreator_5
AttributeCreator_5
    ATTR_TABLE:
      SET_TO PROJNAMN (varchar(200)) = @Left(@Value(PROJEKTNAMN),@FindString(@Value(PROJEKTNAMN)," - "))
      SET_TO PROJEKJTID (int16) = @Right(
          @Value(PROJEKTNAMN),
          @StringLength(@Value(PROJEKTNAMN))
          - @FindString(@Value(PROJEKTNAMN)," - ")
          - 3
        )
    INPUT_PORT_CONNECTED = CONNECTED
    -> AttributeCreator_2
AttributeCreator_2
    ATTR_TABLE:
      SET_TO SAVE_PATH (varchar(200)) = $(ROTMAP)\@Value(PROJNAMN) - @Value(PROJEKJTID)\@Value(FILNAMN)
      SET_TO PROJECT_MAP (varchar(200)) = $(ROTMAP)\@Value(PROJNAMN) - @Value(PROJEKJTID)
    INPUT_PORT_CONNECTED = CONNECTED
    -> Tester_4
Tester_4
    BOOL_OP = OR
    TEST_CLAUSE = TEST @Value(FILTYP) = invalid
    TEST_MODE = TEST
    PASSED -> Terminator_2
    FAILED -> SQLExecutor_3 [INITIATOR]
    FAILED -> Tester_3

Bookmark: Terminator
Note: Om det är ennan filtyp än DWG eller IFC avbryts flödet
Terminator_2
    MESSAGE = Fel filtyp. Måste vara ifc eller dwg.

Bookmark: Registrera metadata och spara fil
Note: Registrerar fil och metadata i PostGIS (lageryta.projekt + lageryta.filer + lageryta.fil_fastighet). Geometri tas från _geometry. / Kopierar originalfilen till $(ROTMAP)\$(PROJEKTNAMN)_$(PROJEKT_ID).
SQLExecutor_3
    COMBINE_ATTRS = Result Attributes Only
    COMBINE_GEOM = Result Geometry Only
    DATASET = relationshandlingar
    FORMAT = POSTGIS
    INPUT_PORT_INITIATOR_CONNECTED = CONNECTED
    OUTPUT_FEATURES = DATA_ONLY
    POSTGIS_CREATE_FEATURE_TABLES_FROM_DATA = Yes
    POSTGIS_DISABLE_COLLECTION_SPLITTING = yes
    POSTGIS_HOST = 172.23.0.154
    POSTGIS_PASSWORD =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
    POSTGIS_PORT = 5432
    POSTGIS_QUERY_FEATURE_TYPES_FOR_MERGE_FILTERS = Yes
    POSTGIS_READ_TIME_WITH_TIMEZONE = Yes
    POSTGIS_SCHEMAS_FOR_TABLE_LISTING = lageryta
    POSTGIS_SSLMODE = prefer
    POSTGIS_USER_NAME = fme_user
    POSTGIS_USE_TRUE_POSTGIS_TYPES = yes
    SQL_STATEMENT:
      FME_SQL_DELIMITER ;

      INSERT INTO lageryta.projekt (projektnummer, projektnamn, rotmapp)
      VALUES ('@Value(PROJEKJTID)', '@Value(PROJNAMN)', '@Value(PROJECT_MAP)')
      ON CONFLICT (projektnummer) DO NOTHING;

      INSERT INTO lageryta.filer (
          projekt_id, lex_diarienummer, filnamn, fil_sokvag,
          filtyp, filstorlek, disciplin, skede, handlingstyp, objekttyp,
          upprattat_av, taggar, sokbar, projektomrade
      ) VALUES (
          (SELECT id FROM lageryta.projekt WHERE projektnummer = '@Value(PROJEKJTID)'),
          NULLIF('$(LEX_DIARIENUMMER)', ''),
          '@Value(FILNAMN)',
          '@Value(SAVE_PATH)',
          '@Value(FILTYP)',
          '@Value(FILSTORLEK)',
          '$(DISCIPLIN)',
          'Relationshandling',
          'Relationshandling',
          COALESCE(NULLIF('$(OBJEKTTYP)', ''), 'Okänd'),
          '$(UPPRATTAD_AV)',
          CASE
              WHEN '$(TAGGAR)' = '' THEN ARRAY[]::TEXT[]
              ELSE ARRAY(SELECT trim(unnest(string_to_array('$(TAGGAR)', ','))))
          END,
          TRUE,
          ST_GeomFromText('@Value(_geometry)', 3011)
      );

      INSERT INTO lageryta.fil_fastighet (fil_id, fastighetsbeteckning)
      SELECT
          currval('lageryta.filer_id_seq'),
          trim(unnest(string_to_array('$(FASTIGHETSBETECKNING)', ',')))
      WHERE '$(FASTIGHETSBETECKNING)' != '';
    INITIATOR -> test00 (writer FILECOPY_1)
test00 (writer FILECOPY_1)

Bookmark: IFC
Note: Om FILTYP=ifc: kör IFC→GLB + planpolygon GeoJSON + metadata JSON via Python (IfcOpenShell/IfcConvert + ev. gltfpack).
PythonCaller_3
    INPUT_PORT_CONNECTED = CONNECTED
    PYTHONSOURCE:
      """
      IFC to GLB + GeoJSON Pipeline for FME PythonCaller
      ===================================================
      Combined module for processing IFC files into:
      - GLB 3D models (with optional rotation and compression)
      - Plan polygon GeoJSON for Cesium/Origo Globe placement
      - Metadata JSON for positioning

      REQUIRED PYTHON PACKAGES (install in FME Python environment):
          pip install ifcopenshell pyproj trimesh pygltflib shapely numpy concave-hull scikit-learn

      REQUIRED EXTERNAL TOOLS:
          - IfcConvert (from IfcOpenShell) - place in tools/ folder or set path in config
          - gltfpack (optional, for compression) - place in tools/ folder or set path

      FEATURE ATTRIBUTES (input):
          - ifc_path (required): Path to the IFC file
          - output_dir (optional): Output directory (default: same as IFC file)
          - ifcconvert_path (optional): Path to ifcconvert.exe
          - gltfpack_path (optional): Path to gltfpack.exe
          - fallback_epsg (optional): Fallback EPSG code (default: 3011)
          - rotation_deg (optional): Rotation degrees (default: 90)
          - rotation_axis (optional): Rotation axis 'x', 'y', or 'z' (default: 'y')
          - keep_intermediate (optional): Keep intermediate files (default: false)

      FEATURE ATTRIBUTES (output):
          - process_status: 'success' or 'error'
          - warnings: JSON array of warnings
          - final_glb: Path to final GLB file
          - plan_geojson: Path to plan polygon GeoJSON
          - meta_json: Path to metadata JSON
          - lat, lon, elevation: Georeferencing data
          - epsg: Detected/used EPSG code
          - epsg_source: 'detected' or 'fallback'
      """
      import fme
      from fme import BaseTransformer
      import fmeobjects


      # Standard library
      import os
      import sys
      import json
      import math
      import shutil
      import subprocess
      from dataclasses import dataclass
      from typing import Dict, Any, Tuple, Optional, List

      # Third-party imports (must be installed in FME's Python environment)
      try:
          import numpy as np
          import ifcopenshell
          from pyproj import Transformer, Geod
          import trimesh
          from pygltflib import GLTF2, Node
          from shapely.geometry import Polygon, mapping, MultiPolygon, Point
          from shapely.geometry.base import BaseGeometry
          from shapely.ops import unary_union
      except ImportError as e:
          raise ImportError(
              f"Missing required package: {e}. "
              "Install required packages in FME Python environment: "
              "pip install ifcopenshell pyproj trimesh pygltflib shapely numpy"
          )

      # Optional packages
      try:
          from concave_hull import concave_hull
      except ImportError:
          concave_hull = None

      try:
          from sklearn.cluster import DBSCAN
      except ImportError:
          DBSCAN = None

      # =============================================================================
      # CONFIGURATION
      # =============================================================================

      @dataclass
      class PipelineConfig:
          """Configuration for the IFC processing pipeline."""
          fallback_epsg: int = 3011
          ifcconvert_path: Optional[str] = None
          gltfpack_path: Optional[str] = None
          output_dir: str = ""
          rotation_axis: str = "y"
          rotation_deg: float = 90.0
          # Hull/cluster settings
          cluster_point_threshold: int = 100000
          cluster_eps: float = 2.0
          cluster_min: int = 50
          keep_noise_cluster: bool = True
          hull_grid: float = 0.02
          hull_stride: int = 2
          hull_concavity: float = 3.5
          hull_length_threshold: float = 0.0
          # Filters (optional)
          use_ifc_filters: bool = False
          ifc_filter: Optional[str] = None
          ifc_filter_lines: Optional[List[str]] = None
          # Output retention
          keep_intermediate_files: bool = False
          # Optional polygons directory for Sweden validation (can be None)
          polygons_dir: Optional[str] = None


      def config_from_feature(feature: fmeobjects.FMEFeature) -> PipelineConfig:
          """Create PipelineConfig from FME feature attributes."""
          cfg = PipelineConfig()

          def get_attr(name: str, default=None):
              val = feature.getAttribute(name)
              return val if val is not None else default

          def get_bool(name: str, default: bool) -> bool:
              val = get_attr(name)
              if val is None:
                  return default
              if isinstance(val, bool):
                  return val
              if isinstance(val, str):
                  return val.lower() in ('true', 'yes', '1')
              return bool(val)

          def get_int(name: str, default: int) -> int:
              val = get_attr(name)
              if val is None:
                  return default
              try:
                  return int(val)
              except (ValueError, TypeError):
                  return default

          def get_float(name: str, default: float) -> float:
              val = get_attr(name)
              if val is None:
                  return default
              try:
                  return float(val)
              except (ValueError, TypeError):
                  return default

          cfg.fallback_epsg = get_int('fallback_epsg', 3011)
          cfg.ifcconvert_path = get_attr('IfcConvert') or get_attr('ifcconvert_path')

          # Get gltfpack path from attribute or FME macro
          cfg.gltfpack_path = get_attr('gltfpack') or get_attr('gltfpack_path')
          if not cfg.gltfpack_path:
              try:
                  cfg.gltfpack_path = feature.getAttribute('gltfpack')
              except Exception:
                  pass

          # Build default output dir from FME macro values
          default_output_dir = ''
          try:
              save_folder = feature.getAttribute('SAVE_PATH')
              print(save_folder)
              default_output_dir = os.path.join(save_folder, 'view')
          except Exception:
              pass

          cfg.output_dir = get_attr('output_dir') or default_output_dir
          cfg.rotation_axis = get_attr('rotation_axis', 'y')
          cfg.rotation_deg = get_float('rotation_deg', 90.0)
          cfg.keep_intermediate_files = get_bool('keep_intermediate', False)
          cfg.hull_concavity = get_float('hull_concavity', 3.5)
          cfg.hull_grid = get_float('hull_grid', 0.02)
          cfg.hull_stride = get_int('hull_stride', 2)
          cfg.cluster_eps = get_float('cluster_eps', 2.0)
          cfg.cluster_min = get_int('cluster_min', 50)
          cfg.cluster_point_threshold = get_int('cluster_point_threshold', 100000)
          cfg.polygons_dir = get_attr('polygons_dir')

          return cfg


      # =============================================================================
      # COORDINATE REFERENCE SYSTEM HANDLING
      # =============================================================================

      _SWEREF_MAP = {
          "SWEREF 99 TM": 3006,
          "SWEREF 99 12 00": 3007,
          "SWEREF 99 13 30": 3008,
          "SWEREF 99 15 00": 3009,
          "SWEREF 99 16 30": 3010,
          "SWEREF 99 18 00": 3011,
          "SWEREF 99 19 30": 3012,
          "SWEREF 99 21 00": 3013,
          "SWEREF 99 22 30": 3014,
          "SWEREF 99 24 00": 3015,
          "SWEREF 99 14 15": 3016,
          "SWEREF 99 15 45": 3017,
          "SWEREF 99 17 15": 3018,
      }

      _DEF_LAT_RANGE = (55.0, 70.5)
      _DEF_LON_RANGE = (10.0, 25.5)


      def _deg_from_dms(dms) -> Optional[float]:
          """Convert DMS (degrees, minutes, seconds) to decimal degrees."""
          if not dms:
              return None
          vals = list(dms)
          sign = -1 if vals[0] < 0 else 1
          vals[0] = abs(vals[0])
          for i in range(1, len(vals)):
              vals[i] = abs(vals[i])
          vals += [0] * (4 - len(vals))
          deg = vals[0] + vals[1] / 60.0 + (vals[2] + vals[3] / 1e6) / 3600.0
          return sign * deg


      def detect_epsg_from_crs(crs: Dict[str, Any], fallback: int) -> Tuple[int, str]:
          """Detect EPSG code from CRS information."""
          if not crs:
              return fallback, "fallback"
          zone = crs.get("map_zone") or crs.get("name") or crs.get("description")
          if zone:
              zone = zone.strip()
              if zone in _SWEREF_MAP:
                  return _SWEREF_MAP[zone], "detected"
              for k, v in _SWEREF_MAP.items():
                  if k.lower() in zone.lower():
                      return v, "detected"
          return fallback, "fallback"


      def _length_unit_info(ifc) -> Dict[str, Any]:
          """Extract length unit information from IFC file."""
          prefix_scale = {
              "EXA": 1e18, "PETA": 1e15, "TERA": 1e12, "GIGA": 1e9, "MEGA": 1e6, "KILO": 1e3,
              "HECTO": 1e2, "DECA": 1e1, "DECI": 1e-1, "CENTI": 1e-2, "MILLI": 1e-3,
              "MICRO": 1e-6, "NANO": 1e-9, "PICO": 1e-12, "FEMTO": 1e-15, "ATTO": 1e-18
          }
          try:
              proj = ifc.by_type("IfcProject")[0]
              ua = getattr(proj, "UnitsInContext", None)
              units = getattr(ua, "Units", []) or []
              for u in units:
                  if hasattr(u, "is_a") and u.is_a("IfcSIUnit") and getattr(u, "UnitType", "") == "LENGTHUNIT":
                      prefix = getattr(u, "Prefix", None)
                      scale = prefix_scale.get(prefix, 1.0)
                      return {"scale_m": scale}
                  if hasattr(u, "is_a") and u.is_a("IfcConversionBasedUnit") and getattr(u, "UnitType", "") == "LENGTHUNIT":
                      vc = getattr(u, "ConversionFactor", None)
                      scale = float(getattr(getattr(vc, "ValueComponent", None), "wrappedValue", 1.0))
                      return {"scale_m": scale}
          except Exception:
              pass
          return {"scale_m": 1.0}


      def _site_placement_offset(site) -> Tuple[float, float, float]:
          """Get site placement offset from IFC site element."""
          try:
              lp = site.ObjectPlacement
              rp = getattr(lp, "RelativePlacement", None)
              loc = getattr(rp, "Location", None)
              coords = getattr(loc, "Coordinates", None)
              if coords:
                  return float(coords[0]), float(coords[1]), float(coords[2]) if len(coords) > 2 else 0.0
          except Exception:
              pass
          return 0.0, 0.0, 0.0


      def get_georef(ifc) -> Dict[str, Any]:
          """Extract georeferencing information from IFC file."""
          info: Dict[str, Any] = {"crs": None, "map_conversion": None, "site": None, "units": {}}
          info["units"]["length"] = _length_unit_info(ifc)

          # CRS & MapConversion (IFC4)
          try:
              projs = ifc.by_type("IfcProjectedCRS")
          except RuntimeError:
              projs = []

          proj = None
          conv = None
          if projs:
              proj = next((p for p in projs if getattr(p, "HasCoordinateOperation", [])), projs[0])
              ops = getattr(proj, "HasCoordinateOperation", [])
              if ops:
                  conv = next((o for o in ops if o.is_a("IfcMapConversion")), None)

          if not conv:
              try:
                  convs = ifc.by_type("IfcMapConversion")
                  conv = convs[0] if convs else None
              except RuntimeError:
                  conv = None

          if proj:
              info["crs"] = {
                  "name": getattr(proj, "Name", None),
                  "description": getattr(proj, "Description", None),
                  "geodetic_datum": getattr(proj, "GeodeticDatum", None),
                  "map_projection": getattr(proj, "MapProjection", None),
                  "map_zone": getattr(proj, "MapZone", None),
              }

          if conv:
              info["map_conversion"] = {
                  "eastings": float(getattr(conv, "Eastings", 0.0) or 0.0),
                  "northings": float(getattr(conv, "Northings", 0.0) or 0.0),
                  "orthogonal_height": float(getattr(conv, "OrthogonalHeight", 0.0) or 0.0),
                  "scale": float(getattr(conv, "Scale", 1.0) or 1.0),
                  "x_axis_abscissa": float(getattr(conv, "XAxisAbscissa", 1.0) or 1.0),
                  "x_axis_ordinate": float(getattr(conv, "XAxisOrdinate", 0.0) or 0.0),
              }

          # Site
          try:
              sites = ifc.by_type("IfcSite")
          except RuntimeError:
              sites = []

          if sites:
              s = sites[0]
              raw_lat = getattr(s, "RefLatitude", None)
              raw_lon = getattr(s, "RefLongitude", None)
              lat = _deg_from_dms(raw_lat)
              lon = _deg_from_dms(raw_lon)
              elev = float(getattr(s, "RefElevation", 0.0) or 0.0)

              # Plausibility check (Sweden bounds)
              if lat is None or not (_DEF_LAT_RANGE[0] <= lat <= _DEF_LAT_RANGE[1]):
                  lat = None
              if lon is None or not (_DEF_LON_RANGE[0] <= lon <= _DEF_LON_RANGE[1]):
                  lon = None

              placement = _site_placement_offset(s)
              info["site"] = {
                  "ref_lat": lat,
                  "ref_lon": lon,
                  "ref_elev": elev,
                  "placement_translation": placement,
              }

          return info


      def compute_offsets(georef: Dict[str, Any], epsg: int) -> Dict[str, Any]:
          """Compute coordinate offsets from georef data."""
          scale_m = georef.get("units", {}).get("length", {}).get("scale_m", 1.0)
          placement = georef.get("site", {}).get("placement_translation", [0.0, 0.0, 0.0])
          if len(placement) < 3:
              placement = list(placement) + [0.0] * (3 - len(placement))

          tx_m = float(placement[0]) * scale_m
          ty_m = float(placement[1]) * scale_m
          tz_m = float(placement[2]) * scale_m
          has_nonzero = any(abs(v) > 1e-6 for v in (tx_m, ty_m))

          latlon_from_placement = None
          if has_nonzero:
              try:
                  transformer = Transformer.from_crs(epsg, 4326, always_xy=True)
                  lon, lat = transformer.transform(tx_m, ty_m)
                  latlon_from_placement = (lat, lon)
              except Exception:
                  latlon_from_placement = None

          return {
              "translation_m": (tx_m, ty_m, tz_m),
              "has_translation": has_nonzero,
              "latlon_from_translation": latlon_from_placement,
          }


      def resolve_model_latlon(georef: Dict[str, Any], offsets: Dict[str, Any]) -> Tuple[Optional[float], Optional[float]]:
          """Resolve model lat/lon from georef and offsets."""
          if offsets.get("latlon_from_translation"):
              return offsets["latlon_from_translation"]
          site = georef.get("site", {})
          return site.get("ref_lat"), site.get("ref_lon")


      # =============================================================================
      # HULL GENERATION
      # =============================================================================

      def load_vertices_xy(glb_path: str) -> np.ndarray:
          """Load XY vertices from GLB file."""
          scene = trimesh.load(glb_path, force='scene')
          if isinstance(scene, trimesh.Scene):
              try:
                  combined = scene.to_geometry()
              except AttributeError:
                  combined = scene.dump(concatenate=True)
              geoms = [combined] if isinstance(combined, trimesh.Trimesh) else (
                  list(combined) if isinstance(combined, (list, tuple)) else [combined]
              )
          else:
              geoms = [scene]

          pts = []
          for g in geoms:
              v = getattr(g, 'vertices', None)
              if v is None or v.size == 0:
                  continue
              # Use X,Z as horizontal plane (Y up)
              v2 = v[:, [0, 2]]
              pts.append(v2)

          if not pts:
              return np.zeros((0, 2), dtype=float)
          return np.vstack(pts).astype(float)


      def concave_or_convex(points: np.ndarray, concavity: float = 3.5, length_threshold: float = 0.0) -> np.ndarray:
          """Generate concave or convex hull from points."""
          if points is None or points.shape[0] < 3:
              return np.zeros((0, 2))

          if concave_hull is not None:
              try:
                  hull = concave_hull(points, concavity=float(concavity), length_threshold=float(length_threshold))
                  H = np.asarray(hull, dtype=float)
                  if H.shape[0] >= 3:
                      if not np.allclose(H[0], H[-1]):
                          H = np.vstack([H, H[0]])
                      return H
              except Exception:
                  pass

          # Fallback to convex hull
          poly_geom = Polygon(points).convex_hull
          if isinstance(poly_geom, Polygon):
              return np.asarray(poly_geom.exterior.coords, dtype=float)
          return np.zeros((0, 2))


      def transform_polygon_local_to_wgs84(coords: np.ndarray, translation_m: Tuple[float, float, float], epsg: int) -> Polygon:
          """Transform local polygon coordinates to WGS84."""
          tx, ty, _ = translation_m
          pts = []
          transformer = Transformer.from_crs(epsg, 4326, always_xy=True)
          for x, y in coords:
              ex = x + tx
              ny = y + ty
              lon, lat = transformer.transform(ex, ny)
              pts.append((lon, lat))
          return Polygon(pts)


      def transform_polygon_local_to_wgs84_ref(coords: np.ndarray, ref_lat: float, ref_lon: float) -> Polygon:
          """Transform local coordinates to WGS84 using geodesic forward from reference point."""
          geod = Geod(ellps='WGS84')
          pts = []
          for x, y in coords:
              az = float(np.degrees(np.arctan2(x, y)))
              dist = float(np.hypot(x, y))
              lon2, lat2, _ = geod.fwd(ref_lon, ref_lat, az, dist)
              pts.append((lon2, lat2))
          return Polygon(pts)


      def write_geojson(plan_poly: BaseGeometry, out_path: str) -> str:
          """Write polygon to GeoJSON file."""
          fc = {"type": "FeatureCollection", "features": []}
          if plan_poly and not plan_poly.is_empty:
              fc["features"].append({
                  "type": "Feature",
                  "geometry": mapping(plan_poly),
                  "properties": {"kind": "model_plan"}
              })
          else:
              fc["features"].append({
                  "type": "Feature",
                  "geometry": None,
                  "properties": {"warning": "empty"}
              })
          with open(out_path, 'w', encoding='utf-8') as f:
              json.dump(fc, f)
          return out_path


      def _prepare_points(points: np.ndarray, grid: float, stride: int, mirror_xy: bool, mirror_x_only: bool) -> np.ndarray:
          """Prepare points for hull generation."""
          P = points
          if mirror_xy:
              P = -P
          if grid and grid > 0:
              P = np.floor(P / float(grid) + 0.5) * float(grid)
          P = np.unique(np.round(P, 8), axis=0)
          if stride and stride > 1:
              P = P[::int(stride)]
          if mirror_x_only:
              P = np.column_stack((-P[:, 0], P[:, 1]))
          return P


      def _cluster_and_hulls(points: np.ndarray, concavity: float, length_threshold: float,
                             cluster_eps: Optional[float], cluster_min: Optional[int],
                             keep_noise: bool = True) -> List[np.ndarray]:
          """Generate hulls with optional DBSCAN clustering."""
          hulls: List[np.ndarray] = []

          if cluster_eps is not None and cluster_min is not None and cluster_min > 0 and DBSCAN is not None:
              labels = DBSCAN(eps=float(cluster_eps), min_samples=int(cluster_min)).fit(points).labels_
              for lab in set(labels):
                  if lab == -1 and not keep_noise:
                      continue
                  pts_lab = points[labels == lab]
                  if pts_lab.shape[0] < 3:
                      continue
                  H = concave_or_convex(pts_lab, concavity=concavity, length_threshold=length_threshold)
                  if H.shape[0] >= 3:
                      hulls.append(H)

          if not hulls:
              H = concave_or_convex(points, concavity=concavity, length_threshold=length_threshold)
              if H.shape[0] >= 3:
                  hulls = [H]

          return hulls


      def generate_plan_geojson(glb_path: str, out_path: str, translation_m: Tuple[float, float, float],
                                epsg: int, concavity: float = 3.5, length_threshold: float = 0.0,
                                grid: float = 0.02, stride: int = 2, mirror_xy: bool = True,
                                cluster_eps: float = 2.0, cluster_min: int = 5,
                                cluster_point_threshold: int = 100000, epsg_source: Optional[str] = None,
                                ref_lat: Optional[float] = None, ref_lon: Optional[float] = None) -> str:
          """Generate plan polygon GeoJSON from GLB file."""
          raw_pts = load_vertices_xy(glb_path)
          pts = _prepare_points(raw_pts, grid=grid, stride=stride, mirror_xy=mirror_xy, mirror_x_only=True)

          do_cluster = (raw_pts.shape[0] >= int(cluster_point_threshold) and
                        cluster_eps is not None and cluster_min is not None)

          hulls = _cluster_and_hulls(
              pts,
              concavity=concavity,
              length_threshold=length_threshold,
              cluster_eps=cluster_eps if do_cluster else None,
              cluster_min=cluster_min if do_cluster else None,
              keep_noise=True,
          )

          tx, ty, _ = translation_m
          if (epsg_source == 'fallback') and (abs(tx) < 1e-6 and abs(ty) < 1e-6) and (ref_lat is not None and ref_lon is not None):
              H = hulls[0] if hulls else np.zeros((0, 2))
              if H.shape[0] >= 3:
                  poly = transform_polygon_local_to_wgs84_ref(H, float(ref_lat), float(ref_lon))
                  return write_geojson(poly, out_path)
              else:
                  geom = Point(float(ref_lon), float(ref_lat))
                  return write_geojson(geom, out_path)

          polys = []
          for H in hulls:
              poly = transform_polygon_local_to_wgs84(H, translation_m, epsg)
              if poly and not poly.is_empty:
                  polys.append(poly)

          union_poly = unary_union(polys) if polys else Polygon()
          return write_geojson(union_poly, out_path)


      # =============================================================================
      # GLTF ROTATION
      # =============================================================================

      def rotate_gltf(in_path: str, out_path: str, axis: str = 'y', angle_deg: float = 90.0) -> str:
          """Rotate GLTF/GLB file by adding a wrapper node."""
          g = GLTF2().load(in_path)
          angle = math.radians(angle_deg)
          half = angle / 2.0
          s = math.sin(half)
          c = math.cos(half)

          qx = qy = qz = 0.0
          axis = axis.lower()
          if axis == 'x':
              qx = s
          elif axis == 'y':
              qy = s
          elif axis == 'z':
              qz = s
          else:
              raise ValueError(f"Unsupported rotation axis: {axis}")
          qw = c

          scene_index = g.scene if isinstance(g.scene, int) else 0
          scene = g.scenes[scene_index]
          original_roots = list(scene.nodes or [])

          wrapper = Node(
              name=f"RotationWrapper_{angle_deg}deg_{axis}",
              rotation=[qx, qy, qz, qw],
              translation=[0, 0, 0],
              scale=[1, 1, 1],
              children=original_roots if original_roots else None
          )

          wrapper_index = len(g.nodes)
          g.nodes.append(wrapper)
          scene.nodes = [wrapper_index]
          g.scenes[scene_index] = scene
          g.save(out_path)
          return out_path


      # =============================================================================
      # COMMAND EXECUTION HELPERS
      # =============================================================================

      def _decode_and_normalize(stdout: bytes, stderr: bytes) -> str:
          """Decode and normalize command output."""
          def decode(b: bytes) -> str:
              for enc in ("utf-16le", "utf-16", "utf-8", "cp1252"):
                  try:
                      s = b.decode(enc, errors="replace")
                      s = s.replace("\u0000", "")
                      return s
                  except Exception:
                      continue
              return b.decode(errors="replace")

          out = decode(stdout or b"")
          err = decode(stderr or b"")

          def collapse_spaced_text(s: str) -> str:
              stripped = s.replace(" ", "")
              if len(stripped) * 2 == len(s):
                  return stripped
              return s

          return collapse_spaced_text(out) + "\n" + collapse_spaced_text(err)


      def run_command_to_file(cmd: List[str], logfile: str, timeout_sec: int = 1800) -> int:
          """Run command and write decoded stdout/stderr to logfile."""
          try:
              p = subprocess.Popen(cmd, stdout=subprocess.PIPE, stderr=subprocess.PIPE)
              try:
                  stdout, stderr = p.communicate(timeout=timeout_sec)
              except subprocess.TimeoutExpired:
                  p.kill()
                  stdout, stderr = p.communicate()
                  text = _decode_and_normalize(stdout, stderr) + "\n[timeout exceeded]\n"
                  with open(logfile, 'w', encoding='utf-8', errors='replace') as lf:
                      lf.write(text)
                  return 124
              text = _decode_and_normalize(stdout, stderr)
              with open(logfile, 'w', encoding='utf-8', errors='replace') as lf:
                  lf.write(text)
              return p.returncode
          except FileNotFoundError:
              with open(logfile, 'w', encoding='utf-8') as lf:
                  lf.write(f"Executable not found: {cmd[0]}\n")
              return 127


      def build_ifcconvert_command(cfg: PipelineConfig, ifc_path: str, out_glb: str,
                                    negative_translation_m: Tuple[float, float, float]) -> List[str]:
          """Build IfcConvert command."""
          tx, ty, tz = negative_translation_m
          cmd = [
              cfg.ifcconvert_path or 'ifcconvert',
              ifc_path,
              out_glb,
              '-j', '7',
              '--kernel', 'hybrid-cgal-simple-opencascade',
              f"--model-offset={tx};{ty};{tz}",
          ]
          return cmd


      def build_gltfpack_command(cfg: PipelineConfig, in_glb: str, out_glb: str) -> List[str]:
          """Build gltfpack command."""
          return [
              cfg.gltfpack_path or 'gltfpack',
              '-i', in_glb,
              '-o', out_glb,
              '-vp', '16', '-mm', '-cc'
          ]


      def _safe_remove(path: Optional[str]) -> None:
          """Safely remove a file if it exists."""
          try:
              if path and os.path.isfile(path):
                  os.remove(path)
          except Exception:
              pass


      def _file_nonempty(path: str, min_bytes: int = 1) -> bool:
          """Check if file exists and is non-empty."""
          try:
              return os.path.isfile(path) and os.path.getsize(path) > min_bytes
          except Exception:
              return False


      # =============================================================================
      # MAIN PIPELINE
      # =============================================================================

      def process_ifc(ifc_path: str, cfg: PipelineConfig) -> Dict[str, Any]:
          """
          Main IFC processing pipeline.

          Args:
              ifc_path: Path to IFC file
              cfg: Pipeline configuration

          Returns:
              Dictionary with processing results including outputs, warnings, and georef data
          """
          result: Dict[str, Any] = {"warnings": [], "steps": []}

          if not os.path.isfile(ifc_path):
              raise FileNotFoundError(f"IFC file not found: {ifc_path}")

          # Determine output directory
          output_dir = cfg.output_dir or os.path.dirname(ifc_path)
          if not output_dir:
              output_dir = os.getcwd()
          os.makedirs(output_dir, exist_ok=True)

          # Open IFC and extract georeferencing
          print(ifc_path)
          ifc = ifcopenshell.open(ifc_path)
          georef = get_georef(ifc)
          epsg, epsg_source = detect_epsg_from_crs(georef.get('crs') or {}, cfg.fallback_epsg)
          georef['units'] = {'length': georef.get('units', {}).get('length', {'scale_m': 1.0})}
          offsets = compute_offsets({'site': georef.get('site'), 'units': georef['units']}, epsg)
          lat, lon = resolve_model_latlon({'site': georef.get('site')}, offsets)

          if epsg_source == 'fallback':
              result['warnings'].append(f"Coordinate system not found; using fallback EPSG {epsg}.")
          if lat is None or lon is None:
              result['warnings'].append('Model geolocation uncertain; using fallback EPSG and origin.')

          translation_m = offsets['translation_m']
          negative_translation = tuple(-v for v in translation_m)

          # Output naming
          base_name = os.path.splitext(os.path.basename(ifc_path))[0]
          raw_glb = os.path.join(output_dir, f"{base_name}_raw.glb")
          rotated_glb = os.path.join(output_dir, f"{base_name}_raw_rot.glb")
          packed_glb = os.path.join(output_dir, f"{base_name}_raw_rot_comp.glb")
          final_glb = os.path.join(output_dir, f"{base_name}.glb")
          plan_geojson = os.path.join(output_dir, f"{base_name}_planpolygon.geojson")
          meta_json = os.path.join(output_dir, f"{base_name}.json")
          ifc_log = os.path.join(output_dir, f"{base_name}_ifcconvert.log")
          pack_log = os.path.join(output_dir, f"{base_name}_gltfpack.log")

          # Pre-run cleanup
          for p in (raw_glb, rotated_glb, packed_glb, final_glb, plan_geojson, meta_json, ifc_log, pack_log):
              _safe_remove(p)

          # 1. IfcConvert
          if cfg.ifcconvert_path:
              cmd_ifc = build_ifcconvert_command(cfg, ifc_path, raw_glb, negative_translation)
              code = run_command_to_file(cmd_ifc, ifc_log)
              result['steps'].append({'cmd': cmd_ifc, 'code': code, 'logfile': ifc_log})
              if code != 0:
                  result['warnings'].append('IfcConvert failed; subsequent steps may be invalid.')
          else:
              result['warnings'].append('IfcConvert not configured; skipping GLB conversion.')

          # 2. Plan polygon (only if raw_glb exists)
          if os.path.isfile(raw_glb):
              try:
                  generate_plan_geojson(
                      raw_glb,
                      plan_geojson,
                      translation_m,
                      epsg,
                      concavity=cfg.hull_concavity,
                      length_threshold=cfg.hull_length_threshold,
                      grid=cfg.hull_grid,
                      stride=cfg.hull_stride,
                      mirror_xy=True,
                      cluster_eps=cfg.cluster_eps,
                      cluster_min=cfg.cluster_min,
                      cluster_point_threshold=cfg.cluster_point_threshold,
                      epsg_source=epsg_source,
                      ref_lat=lat,
                      ref_lon=lon,
                  )
              except Exception as e:
                  result['warnings'].append(f'Failed to generate plan polygon: {e}')
          else:
              result['warnings'].append('Raw GLB missing; skipping plan polygon generation.')

          # 3. Rotation
          if os.path.isfile(raw_glb):
              try:
                  rotate_gltf(raw_glb, rotated_glb, axis=cfg.rotation_axis, angle_deg=cfg.rotation_deg)
              except Exception as e:
                  result['warnings'].append(f'Rotation failed: {e}')
          else:
              result['warnings'].append('Raw GLB missing; skipping rotation.')

          # 4. Packing (optional)
          if os.path.isfile(rotated_glb) and cfg.gltfpack_path:
              cmd_pack = build_gltfpack_command(cfg, rotated_glb, packed_glb)
              code = run_command_to_file(cmd_pack, pack_log)
              result['steps'].append({'cmd': cmd_pack, 'code': code, 'logfile': pack_log})
              if not _file_nonempty(pack_log):
                  _safe_remove(pack_log)
              if code != 0:
                  result['warnings'].append('gltfpack failed.')
          elif not cfg.gltfpack_path:
              result['warnings'].append('gltfpack not configured; skipping compression.')
          elif not os.path.isfile(rotated_glb):
              result['warnings'].append('Rotated GLB missing; packing step skipped.')

          # Determine final GLB and optionally clean intermediates
          final_path = None
          if os.path.isfile(packed_glb):
              final_path = packed_glb
          elif os.path.isfile(rotated_glb):
              final_path = rotated_glb
          elif os.path.isfile(raw_glb):
              final_path = raw_glb

          keep_intermediate = cfg.keep_intermediate_files
          if final_path:
              if not keep_intermediate and final_path != final_glb:
                  try:
                      _safe_remove(final_glb)
                      shutil.move(final_path, final_glb)
                      final_path = final_glb
                  except Exception as e:
                      result['warnings'].append(f'Failed to rename final GLB: {e}')
              if not keep_intermediate:
                  for p in (raw_glb, rotated_glb, packed_glb):
                      if p != final_path:
                          _safe_remove(p)

          # 5. Metadata JSON
          tx_m, ty_m, tz_m = translation_m if isinstance(translation_m, (list, tuple)) else (0, 0, 0)
          site_info = georef.get('site', {}) if isinstance(georef, dict) else {}
          ref_elev = site_info.get('ref_elev', 0.0)

          height_val = 0
          if abs(tz_m) > 1e-6:
              height_val = tz_m
          else:
              xy_zero = (abs(tx_m) <= 1e-6 and abs(ty_m) <= 1e-6 and abs(tz_m) <= 1e-6)
              if xy_zero and (lat is not None and lon is not None) and abs(ref_elev or 0.0) > 1e-6:
                  height_val = float(ref_elev)

          gltf_entry = {
              'url': os.path.basename(final_path) if final_path and os.path.isfile(final_path) else None,
              'lat': lat if (lat is not None) else 0,
              'lng': lon if (lon is not None) else 0,
              'height': height_val,
              'heightReference': 'NONE',
              'rotHeading': 0,
              'animation': False
          }

          meta = {
              'gltf': [gltf_entry],
              'epsg': epsg,
              'translation_m': translation_m,
              'warnings': result['warnings']
          }

          try:
              with open(meta_json, 'w', encoding='utf-8') as f:
                  json.dump(meta, f, indent=2)
          except Exception as e:
              result['warnings'].append(f'Failed writing metadata JSON: {e}')

          result['outputs'] = {
              'raw_glb': raw_glb if os.path.isfile(raw_glb) else None,
              'rotated_glb': rotated_glb if os.path.isfile(rotated_glb) else None,
              'packed_glb': packed_glb if os.path.isfile(packed_glb) else None,
              'final_glb': final_path if (final_path and os.path.isfile(final_path)) else None,
              'plan_geojson': plan_geojson if os.path.isfile(plan_geojson) else None,
              'meta_json': meta_json if os.path.isfile(meta_json) else None,
          }
          result['georef'] = georef
          result['epsg'] = epsg
          result['epsg_source'] = epsg_source
          result['lat'] = lat
          result['lon'] = lon
          result['elevation'] = height_val

          return result


      # =============================================================================
      # FME PYTHONCALLER CLASS
      # =============================================================================

      class FeatureProcessor(BaseTransformer):
          """
          FME PythonCaller class for IFC to GLB + GeoJSON processing.

          This class processes IFC files and outputs:
          - GLB 3D model (with optional rotation and compression)
          - Plan polygon GeoJSON for Cesium placement
          - Metadata JSON with positioning information

          Usage:
          1. Set 'Class to Process Features' to 'FeatureProcessor'
          2. Input features should have 'ifc_path' attribute
          3. Optional: Set ifcconvert_path, gltfpack_path, output_dir, etc.
          """

          def __init__(self):
              """Initialize the FeatureProcessor."""
              super().__init__()
              self._error_count = 0
              self._success_count = 0


          def has_support_for(self, support_type: int):
              """FME support query - enable bulk mode for performance."""
              return support_type == fmeobjects.FME_SUPPORT_FEATURE_TABLE_SHIM

          def input(self, feature: fmeobjects.FMEFeature):
              """
              Process each incoming feature.

              Expects feature attribute 'ifc_path' or 'path' with path to IFC file.
              Optional attributes for configuration (see module docstring).
              """

              for p in sys.path:
                  fmeobjects.FMELogFile().logMessageString('PYTHONPATH: ' + p)

              try:
                  # Get IFC path from feature - try filecopy_source_dataset first, then ifc_path
                  ifc_path = feature.getAttribute('path')

                  # Log what we're trying to read
                  print(f"[IFC2Geo] Attempting to read IFC path from 'path': {ifc_path}")

                  if not ifc_path:
                      # Try fallback attribute
                      ifc_path = feature.getAttribute('ifc_path')
                      print(f"[IFC2Geo] Fallback - reading from 'ifc_path': {ifc_path}")

                  if not ifc_path:
                      # Log all attributes to help debug
                      all_attrs = feature.getAllAttributeNames()
                      print(f"[IFC2Geo] ERROR: No IFC path found. Available attributes: {list(all_attrs)}")
                      self.reject_feature(feature, "MISSING_IFC_PATH",
                                         "Feature missing required 'path' or 'ifc_path' attribute")
                      return

                  # Check if file exists
                  if not os.path.isfile(ifc_path):
                      print(f"[IFC2Geo] ERROR: IFC file does not exist: {ifc_path}")
                      self.reject_feature(feature, "FILE_NOT_FOUND", f"IFC file not found: {ifc_path}")
                      return

                  print(f"[IFC2Geo] Processing IFC file: {ifc_path}")

                  # Build configuration from feature attributes
                  cfg = config_from_feature(feature)

                  # Process the IFC file
                  result = process_ifc(ifc_path, cfg)

                  # Set output attributes
                  feature.setAttribute('process_status', 'success')
                  feature.setAttribute('warnings', json.dumps(result.get('warnings', [])))

                  # Output file paths
                  outputs = result.get('outputs', {})
                  feature.setAttribute('final_glb', outputs.get('final_glb', ''))
                  feature.setAttribute('plan_geojson', outputs.get('plan_geojson', ''))
                  feature.setAttribute('meta_json', outputs.get('meta_json', ''))
                  feature.setAttribute('raw_glb', outputs.get('raw_glb', ''))
                  feature.setAttribute('rotated_glb', outputs.get('rotated_glb', ''))
                  feature.setAttribute('packed_glb', outputs.get('packed_glb', ''))

                  # Georeferencing data
                  feature.setAttribute('lat', result.get('lat'))
                  feature.setAttribute('lon', result.get('lon'))
                  feature.setAttribute('elevation', result.get('elevation', 0))
                  feature.setAttribute('epsg', result.get('epsg'))
                  feature.setAttribute('epsg_source', result.get('epsg_source', ''))

                  # Translation values
                  translation = result.get('georef', {}).get('site', {}).get('placement_translation', (0, 0, 0))
                  if translation:
                      feature.setAttribute('translation_x', translation[0] if len(translation) > 0 else 0)
                      feature.setAttribute('translation_y', translation[1] if len(translation) > 1 else 0)
                      feature.setAttribute('translation_z', translation[2] if len(translation) > 2 else 0)

                  self._success_count += 1
                  self.pyoutput(feature, output_tag="PYOUTPUT")

              except FileNotFoundError as e:
                  self.reject_feature(feature, "FILE_NOT_FOUND", str(e))
                  self._error_count += 1

              except Exception as e:
                  self.reject_feature(feature, "PROCESSING_ERROR", str(e))
                  self._error_count += 1

          def close(self):
              """Called after all features have been processed."""
              # Log processing summary
              print(f"IFC2Geo Processing complete: {self._success_count} success, {self._error_count} errors")

          def process_group(self):
              """Called by FME for each group when group processing mode is enabled."""
              pass

          def reject_feature(self, feature: fmeobjects.FMEFeature, code: str, message: str):
              """Output a feature to the <Rejected> port with error details."""
              feature.setAttribute("fme_rejection_code", code)
              feature.setAttribute("fme_rejection_message", message)
              feature.setAttribute("process_status", "error")
              self.pyoutput(feature, output_tag="<Rejected>")


      # =============================================================================
      # STANDALONE USAGE (for testing outside FME)
      # =============================================================================

      def _run_standalone():
          """Run standalone CLI mode. Only called when script is run directly with arguments."""
          import argparse

          parser = argparse.ArgumentParser(description='IFC to GLB + GeoJSON pipeline (standalone)')
          parser.add_argument('ifc', help='Path to IFC file')
          parser.add_argument('--output-dir', '-o', help='Output directory')
          parser.add_argument('--ifcconvert', help='Path to ifcconvert executable')
          parser.add_argument('--gltfpack', help='Path to gltfpack executable')
          parser.add_argument('--epsg', type=int, default=3011, help='Fallback EPSG code')
          args = parser.parse_args()

          cfg = PipelineConfig(
              fallback_epsg=args.epsg,
              ifcconvert_path=args.ifcconvert,
              gltfpack_path=args.gltfpack,
              output_dir=args.output_dir or '',
          )

          result = process_ifc(args.ifc, cfg)
          print(json.dumps(result, indent=2, default=str))


      # Only run standalone mode if:
      # 1. Script is run directly (__name__ == '__main__')
      # 2. There are command-line arguments (FME imports with no args)
      # 3. First argument looks like an IFC file path (not FME internal)
      if __name__ == '__main__':
          if len(sys.argv) > 1 and (sys.argv[1].lower().endswith('.ifc') or sys.argv[1].startswith('-')):
              _run_standalone()
    PYTHONSYMBOL = FeatureProcessor

Bookmark: DWG
Note: Skickar DWG-jobb till FME Flow (dwg2view.fmw) med parametrar; väntar på resultat.
WorkspaceRunner [off]
    BLOCKING = No
    INPUT_PORT_CONNECTED = CONNECTED
    MAX_TO_BATCH = 1
    OVERWRITE_LOG_FILE = HONOR
    WORKSPACE_FILE = $(FME_MF_DIR_ENCODED)dwg2view.fmw
    WORKSPACE_PARAMETERS = GLB,,ROTMAP,$(ROTMAP),GLTFPACK,$(GLTFPACK),FILENAME,@Value(FILNAMN),filecopy_source_dataset,@Value(path),SAVE_PATH,@Value(SAVE_PATH)
FMEFlowJobSubmitter
    ACTION = SUBMIT_JOB
    BLOCKING = TRUE
    REPOSITORY = Relationshandlingar
    SERVER_CONNECTION = fmeserver
    WORKSPACE_NAME = dwg2view.fmw
    WORKSPACE_PARAMETERS = ROTMAP string $(ROTMAP) GLTFPACK string $(GLTFPACK) FILENAME string @Value(FILNAMN) filecopy_source_dataset list @Value(path) SAVE_PATH string @Value(SAVE_PATH)
