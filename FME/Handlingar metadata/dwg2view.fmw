FME workspace dwg2view.fmw

Parameters:
- GLB =   # Parameter Group
- ROTMAP = C:\Users\SEIAMM\OneDrive - Sweco AB\Documents\Uppdrag\Tyresö\lageryta
- GLTFPACK = C:\Users\SEIAMM\Downloads\gltfpack-windows\gltfpack.exe
- FILENAME = L-30-P-001
- filecopy_source_dataset = C:\Users\SEIAMM\Downloads\L-30-P-001.dwg
- SAVE_PATH = C:\Users\SEIAMM\OneDrive - Sweco AB\Documents\Uppdrag\Tyresö\lageryta\test99111_128\L-30-P-001

Readers:
- ACAD_1: ACAD from $(filecopy_source_dataset)

Writers:
- ACAD_2: ACAD to $(SAVE_PATH)\view\$(FILENAME).dxf

0 (reader ACAD_1)
    -> FeatureMerger [REQUESTOR]
    -> Sampler

Bookmark: KOntrollerar om DWG:-filen innhåller 3D-data
Sampler
    MODE = RANDOM
    RATE = 50
    SAMPLE_TYPE_MULTIPLIER = 1
    SAMPLE_MODE = Yes
    SAMPLE_TYPE_LONG = Every Nth Feature
    SAMPLED -> GeometryFilter
GeometryFilter
    FILTER_MODE = COMPLETE
    FILTER_MULTI = FILTER_TYPES]GeometryInstance Aggregate Area Donut SimpleArea Ellipse Polygon Curve Path Segment Arc BSpline Clothoid Line OrientedArc MultiArea MultiCurve MultiPoint MultiSolid MultiSurface MultiText Null Point PointCloud Raster Solid CompositeSolid SimpleSolid BRepSolid Box CSGSolid Extrusion Pipe Surface CompositeSurface SimpleSurface Face Mesh RectangleFace TriangleFan TriangleStrip Text VoxelGrid]FILTER_TYPES_Complete]GeometryInstance Aggregate Area Donut SimpleArea Ellipse Polygon Curve Path Segment Arc BSpline Clothoid Line OrientedArc MultiArea MultiCurve MultiPoint MultiSolid MultiSurface MultiText Null Point PointCloud Raster Solid CompositeSolid SimpleSolid BRepSolid Box CSGSolid Extrusion Pipe Surface CompositeSurface SimpleSurface Face Mesh RectangleFace TriangleFan TriangleStrip Text VoxelGrid]INSTANCES]INSTANCE
    FILTER_TYPES = GeometryInstance Aggregate Area Donut SimpleArea Ellipse Polygon Curve Path Segment Arc BSpline Clothoid Line OrientedArc MultiArea MultiCurve MultiPoint MultiSolid MultiSurface MultiText Null Point PointCloud Raster Solid CompositeSolid SimpleSolid BRepSolid Box CSGSolid Extrusion Pipe Surface CompositeSurface SimpleSurface Face Mesh RectangleFace TriangleFan TriangleStrip Text VoxelGrid
    FILTER_TYPES_Complete = GeometryInstance Aggregate Area Donut SimpleArea Ellipse Polygon Curve Path Segment Arc BSpline Clothoid Line OrientedArc MultiArea MultiCurve MultiPoint MultiSolid MultiSurface MultiText Null Point PointCloud Raster Solid CompositeSolid SimpleSolid BRepSolid Box CSGSolid Extrusion Pipe Surface CompositeSurface SimpleSurface Face Mesh RectangleFace TriangleFan TriangleStrip Text VoxelGrid
    INSTANCES = INSTANCE
    Mesh -> StatisticsCalculator
    Solid -> StatisticsCalculator
    SimpleSolid -> StatisticsCalculator
    BRepSolid -> StatisticsCalculator
StatisticsCalculator
    ATTR_ACCUM_MODE = None
    CALCULATION_MODE = NUMERIC
    FEAT_STATS = fme_feature_type,NUMERIC_MODE,,,COUNT,,,,,,,,,,
    SUMMARY -> FeatureMerger [SUPPLIER]
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Tester
    UNMERGED_REQUESTOR -> Tester
Tester
    BOOL_OP = OR
    TEST_CLAUSE = TEST @Value(fme_feature_type.total_count) > 0
    TEST_MODE = TEST
    PASSED -> PythonCaller
    FAILED -> Layer1 (writer ACAD_2)

Bookmark: Om filen innehåller 3D-data så skapas en glb-fil med hjälp av ett python script
PythonCaller
    INPUT_PORT_CONNECTED = CONNECTED
    PYTHONSOURCE:
      """
      DWG/DWF to GLB + GeoJSON Pipeline for FME PythonCaller
      =======================================================
      Combined module for processing DWG/DWF files into:
      - GLB 3D models (with optional rotation and compression)
      - Plan polygon GeoJSON for Cesium/Origo Globe placement
      - Metadata JSON for positioning

      This script works in TWO modes:
      1. FME Geometry Mode (RECOMMENDED): FME reads DWG/DWF and passes 3D geometry features
      2. External Converter Mode: Uses ODA File Converter to convert DWG → OBJ → GLB

      REQUIRED PYTHON PACKAGES (install in FME Python environment):
          pip install pyproj trimesh pygltflib shapely numpy

      OPTIONAL PACKAGES (for better polygon generation):
          pip install concave-hull scikit-learn scipy

      OPTIONAL EXTERNAL TOOLS:
          - ODA File Converter (for standalone DWG conversion) - https://www.opendesign.com/guestfiles/oda_file_converter
          - gltfpack (optional, for compression) - https://github.com/zeux/meshoptimizer

      FEATURE ATTRIBUTES (input):
          - dwg_path or filecopy_source_dataset (required in External mode): Path to DWG/DWF file
          - output_dir (optional): Output directory (default: SAVE_FOLDER/PROJEKTNAMN or same as DWG)
          - oda_converter_path (optional): Path to ODAFileConverter.exe
          - gltfpack_path (optional): Path to gltfpack.exe
          - source_epsg (optional): Source EPSG code for coordinates (default: 3011)
          - fallback_epsg (optional): Fallback EPSG code (default: 3011)
          - rotation_deg (optional): Rotation degrees (default: 90)
          - rotation_axis (optional): Rotation axis 'x', 'y', or 'z' (default: 'y')
          - ref_lat, ref_lon (optional): Reference lat/lon for georeferencing
          - ref_elevation (optional): Reference elevation (default: 0)
          - keep_intermediate (optional): Keep intermediate files (default: false)

      FEATURE ATTRIBUTES (output):
          - process_status: 'success' or 'error'
          - warnings: JSON array of warnings
          - final_glb: Path to final GLB file
          - plan_geojson: Path to plan polygon GeoJSON
          - meta_json: Path to metadata JSON
          - lat, lon, elevation: Georeferencing data
          - epsg: Used EPSG code
          - geometry_count: Number of geometries processed (GeometryProcessor mode)
          - centroid_x, centroid_y, centroid_z: Calculated centroid (GeometryProcessor mode)

      =============================================================================
      FME GEOMETRY MODE USAGE (RECOMMENDED for DWG files):
      =============================================================================
          1. Use Autodesk AutoCAD DWG/DXF Reader to read DWG file
          2. Optionally filter to get 3D geometry (Solids, Surfaces, 3DMeshes, etc.)
          3. Connect to PythonCaller with this script
          4. Set 'Class to Process Features' to 'GeometryProcessor'
          5. Set Group Processing to 'Feature by Feature but Preserving Groups'
          6. GroupBy: fme_basename (to process each DWG file separately)

          Supported FME geometry types:
          - FMEMesh (native meshes)
          - FMESolid, FMEBRepSolid (solid bodies)
          - FMESurface, FMEFace (individual surfaces)
          - FMEMultiSurface, FMECompositeSurface (multi-part surfaces)
          - FMEAggregate (collections)

      =============================================================================
      EXTERNAL CONVERTER MODE USAGE (if FME cannot read the geometry):
      =============================================================================
          1. Use Directory/File Reader to list DWG files
          2. Connect to PythonCaller with this script
          3. Set 'Class to Process Features' to 'FileProcessor'
          4. Set 'ODAConverter' attribute (or oda_converter_path) to path of ODAFileConverter.exe
      """
      import fme
      from fme import BaseTransformer
      import fmeobjects

      # Standard library
      import os
      import sys
      import json
      import math
      import shutil
      import subprocess
      import tempfile
      from dataclasses import dataclass
      from typing import Dict, Any, Tuple, Optional, List

      # Third-party imports (must be installed in FME's Python environment)
      try:
          import numpy as np
          from pyproj import Transformer, Geod
          import trimesh
          from pygltflib import GLTF2, Node
          from shapely.geometry import Polygon, mapping, MultiPolygon, Point
          from shapely.geometry.base import BaseGeometry
          from shapely.ops import unary_union
      except ImportError as e:
          raise ImportError(
              f"Missing required package: {e}. "
              "Install required packages in FME Python environment: "
              "pip install pyproj trimesh pygltflib shapely numpy"
          )

      # Optional packages
      try:
          from concave_hull import concave_hull
      except ImportError:
          concave_hull = None

      try:
          from sklearn.cluster import DBSCAN
      except ImportError:
          DBSCAN = None


      # =============================================================================
      # CONFIGURATION
      # =============================================================================

      @dataclass
      class PipelineConfig:
          """Configuration for the DWG processing pipeline (3D DWG only)."""
          source_epsg: int = 3011
          fallback_epsg: int = 3011
          oda_converter_path: Optional[str] = None
          gltfpack_path: Optional[str] = None
          output_dir: str = ""
          rotation_axis: str = "y"
          rotation_deg: float = 90.0
          ref_lat: Optional[float] = None
          ref_lon: Optional[float] = None
          ref_elevation: float = 0.0
          # Mesh simplification
          simplify_mesh: bool = False  # Enable mesh simplification (requires scipy)
          simplify_ratio: float = 1  # Target ratio (1 = keep original, 0.9 = reduce to 90% of original)
          merge_vertices: bool = True  # Merge duplicate/close vertices
          merge_tolerance: float = 0.005  # Tolerance for vertex merging (meters)
          # Hull/cluster settings
          cluster_point_threshold: int = 100000
          cluster_eps: float = 2.0
          cluster_min: int = 50
          hull_grid: float = 0.02
          hull_stride: int = 2
          hull_concavity: float = 3.5
          hull_length_threshold: float = 0.0
          # Output retention
          keep_intermediate_files: bool = False


      def config_from_feature(feature: fmeobjects.FMEFeature) -> PipelineConfig:
          """Create PipelineConfig from FME feature attributes."""
          cfg = PipelineConfig()

          def get_attr(name: str, default=None):
              val = feature.getAttribute(name)
              return val if val is not None else default

          def get_bool(name: str, default: bool) -> bool:
              val = get_attr(name)
              if val is None:
                  return default
              if isinstance(val, bool):
                  return val
              if isinstance(val, str):
                  return val.lower() in ('true', 'yes', '1')
              return bool(val)

          def get_int(name: str, default: int) -> int:
              val = get_attr(name)
              if val is None:
                  return default
              try:
                  return int(val)
              except (ValueError, TypeError):
                  return default

          def get_float(name: str, default: float) -> float:
              val = get_attr(name)
              if val is None:
                  return default
              try:
                  return float(val)
              except (ValueError, TypeError):
                  return default

          cfg.source_epsg = get_int('source_epsg', 3011)
          cfg.fallback_epsg = get_int('fallback_epsg', 3011)
          cfg.oda_converter_path = get_attr('ODAConverter') or get_attr('oda_converter_path')

          # Get gltfpack path from attribute or FME macro
          cfg.gltfpack_path = get_attr('gltfpack') or get_attr('gltfpack_path')
          if not cfg.gltfpack_path:
              try:
                  cfg.gltfpack_path = fme.macroValues['GLTFPACK']
              except Exception:
                  pass

          # Build default output dir from FME macro values
          default_output_dir = ''
          try:
              save_folder = fme.macroValues['SAVE_PATH']
              print(save_folder)
              default_output_dir = os.path.join(save_folder, 'view')
          except Exception:
              pass

          cfg.output_dir = get_attr('output_dir') or default_output_dir
          cfg.rotation_axis = get_attr('rotation_axis', 'y')
          cfg.rotation_deg = get_float('rotation_deg', 90.0)
          cfg.ref_lat = get_float('ref_lat', None) if get_attr('ref_lat') else None
          cfg.ref_lon = get_float('ref_lon', None) if get_attr('ref_lon') else None
          cfg.ref_elevation = get_float('ref_elevation', 0.0)
          cfg.keep_intermediate_files = get_bool('keep_intermediate', False)
          cfg.hull_concavity = get_float('hull_concavity', 3.5)
          cfg.hull_grid = get_float('hull_grid', 0.02)
          cfg.hull_stride = get_int('hull_stride', 2)
          cfg.cluster_eps = get_float('cluster_eps', 2.0)
          cfg.cluster_min = get_int('cluster_min', 50)
          cfg.cluster_point_threshold = get_int('cluster_point_threshold', 100000)
          # Mesh simplification settings
          cfg.simplify_mesh = get_bool('simplify_mesh', False)
          cfg.simplify_ratio = get_float('simplify_ratio', 1.0)
          cfg.merge_vertices = get_bool('merge_vertices', True)
          cfg.merge_tolerance = get_float('merge_tolerance', 0.005)

          return cfg


      # =============================================================================
      # COORDINATE REFERENCE SYSTEM HANDLING
      # =============================================================================

      _SWEREF_MAP = {
          "SWEREF 99 TM": 3006,
          "SWEREF 99 12 00": 3007,
          "SWEREF 99 13 30": 3008,
          "SWEREF 99 15 00": 3009,
          "SWEREF 99 16 30": 3010,
          "SWEREF 99 18 00": 3011,
          "SWEREF 99 19 30": 3012,
          "SWEREF 99 21 00": 3013,
          "SWEREF 99 22 30": 3014,
          "SWEREF 99 24 00": 3015,
          "SWEREF 99 14 15": 3016,
          "SWEREF 99 15 45": 3017,
          "SWEREF 99 17 15": 3018,
      }

      _DEF_LAT_RANGE = (55.0, 70.5)
      _DEF_LON_RANGE = (10.0, 25.5)


      def transform_coords_to_wgs84(x: float, y: float, epsg: int) -> Tuple[float, float]:
          """Transform coordinates from source EPSG to WGS84."""
          try:
              transformer = Transformer.from_crs(epsg, 4326, always_xy=True)
              lon, lat = transformer.transform(x, y)
              return lat, lon
          except Exception:
              return None, None


      def validate_latlon(lat: Optional[float], lon: Optional[float]) -> Tuple[Optional[float], Optional[float]]:
          """Validate lat/lon are within Sweden bounds."""
          if lat is None or not (_DEF_LAT_RANGE[0] <= lat <= _DEF_LAT_RANGE[1]):
              lat = None
          if lon is None or not (_DEF_LON_RANGE[0] <= lon <= _DEF_LON_RANGE[1]):
              lon = None
          return lat, lon


      # =============================================================================
      # HULL GENERATION
      # =============================================================================

      def load_vertices_xy(glb_path: str) -> np.ndarray:
          """Load XY vertices from GLB file."""
          scene = trimesh.load(glb_path, force='scene')
          if isinstance(scene, trimesh.Scene):
              try:
                  combined = scene.to_geometry()
              except AttributeError:
                  combined = scene.dump(concatenate=True)
              geoms = [combined] if isinstance(combined, trimesh.Trimesh) else (
                  list(combined) if isinstance(combined, (list, tuple)) else [combined]
              )
          else:
              geoms = [scene]

          pts = []
          for g in geoms:
              v = getattr(g, 'vertices', None)
              if v is None or v.size == 0:
                  continue
              # Use X,Z as horizontal plane (Y up in GLB)
              v2 = v[:, [0, 2]]
              pts.append(v2)

          if not pts:
              return np.zeros((0, 2), dtype=float)
          return np.vstack(pts).astype(float)


      def concave_or_convex(points: np.ndarray, concavity: float = 3.5, length_threshold: float = 0.0) -> np.ndarray:
          """Generate concave or convex hull from points."""
          if points is None or points.shape[0] < 3:
              return np.zeros((0, 2))

          if concave_hull is not None:
              try:
                  hull = concave_hull(points, concavity=float(concavity), length_threshold=float(length_threshold))
                  H = np.asarray(hull, dtype=float)
                  if H.shape[0] >= 3:
                      if not np.allclose(H[0], H[-1]):
                          H = np.vstack([H, H[0]])
                      return H
              except Exception:
                  pass

          # Fallback to convex hull
          poly_geom = Polygon(points).convex_hull
          if isinstance(poly_geom, Polygon):
              return np.asarray(poly_geom.exterior.coords, dtype=float)
          return np.zeros((0, 2))


      def transform_polygon_local_to_wgs84(coords: np.ndarray, translation_m: Tuple[float, float, float], epsg: int) -> Polygon:
          """Transform local polygon coordinates to WGS84."""
          tx, ty, _ = translation_m
          pts = []
          transformer = Transformer.from_crs(epsg, 4326, always_xy=True)
          for x, y in coords:
              ex = x + tx
              ny = y + ty
              lon, lat = transformer.transform(ex, ny)
              pts.append((lon, lat))
          return Polygon(pts)


      def transform_polygon_local_to_wgs84_ref(coords: np.ndarray, ref_lat: float, ref_lon: float) -> Polygon:
          """Transform local coordinates to WGS84 using geodesic forward from reference point."""
          geod = Geod(ellps='WGS84')
          pts = []
          for x, y in coords:
              az = float(np.degrees(np.arctan2(x, y)))
              dist = float(np.hypot(x, y))
              lon2, lat2, _ = geod.fwd(ref_lon, ref_lat, az, dist)
              pts.append((lon2, lat2))
          return Polygon(pts)


      def write_geojson(plan_poly: BaseGeometry, out_path: str) -> str:
          """Write polygon to GeoJSON file."""
          fc = {"type": "FeatureCollection", "features": []}
          if plan_poly and not plan_poly.is_empty:
              fc["features"].append({
                  "type": "Feature",
                  "geometry": mapping(plan_poly),
                  "properties": {"kind": "model_plan"}
              })
          else:
              fc["features"].append({
                  "type": "Feature",
                  "geometry": None,
                  "properties": {"warning": "empty"}
              })
          with open(out_path, 'w', encoding='utf-8') as f:
              json.dump(fc, f)
          return out_path


      def _prepare_points(points: np.ndarray, grid: float, stride: int, mirror_xy: bool, mirror_x_only: bool) -> np.ndarray:
          """Prepare points for hull generation."""
          P = points
          if mirror_xy:
              P = -P
          if grid and grid > 0:
              P = np.floor(P / float(grid) + 0.5) * float(grid)
          P = np.unique(np.round(P, 8), axis=0)
          if stride and stride > 1:
              P = P[::int(stride)]
          if mirror_x_only:
              P = np.column_stack((-P[:, 0], P[:, 1]))
          return P


      def _cluster_and_hulls(points: np.ndarray, concavity: float, length_threshold: float,
                             cluster_eps: Optional[float], cluster_min: Optional[int],
                             keep_noise: bool = True) -> List[np.ndarray]:
          """Generate hulls with optional DBSCAN clustering."""
          hulls: List[np.ndarray] = []

          if cluster_eps is not None and cluster_min is not None and cluster_min > 0 and DBSCAN is not None:
              labels = DBSCAN(eps=float(cluster_eps), min_samples=int(cluster_min)).fit(points).labels_
              for lab in set(labels):
                  if lab == -1 and not keep_noise:
                      continue
                  pts_lab = points[labels == lab]
                  if pts_lab.shape[0] < 3:
                      continue
                  H = concave_or_convex(pts_lab, concavity=concavity, length_threshold=length_threshold)
                  if H.shape[0] >= 3:
                      hulls.append(H)

          if not hulls:
              H = concave_or_convex(points, concavity=concavity, length_threshold=length_threshold)
              if H.shape[0] >= 3:
                  hulls = [H]

          return hulls


      def generate_plan_geojson(glb_path: str, out_path: str, translation_m: Tuple[float, float, float],
                                epsg: int, concavity: float = 3.5, length_threshold: float = 0.0,
                                grid: float = 0.02, stride: int = 2, mirror_xy: bool = True,
                                cluster_eps: float = 2.0, cluster_min: int = 5,
                                cluster_point_threshold: int = 100000,
                                ref_lat: Optional[float] = None, ref_lon: Optional[float] = None,
                                use_ref_coords: bool = False) -> str:
          """Generate plan polygon GeoJSON from GLB file."""
          raw_pts = load_vertices_xy(glb_path)
          pts = _prepare_points(raw_pts, grid=grid, stride=stride, mirror_xy=mirror_xy, mirror_x_only=True)

          do_cluster = (raw_pts.shape[0] >= int(cluster_point_threshold) and
                        cluster_eps is not None and cluster_min is not None)

          hulls = _cluster_and_hulls(
              pts,
              concavity=concavity,
              length_threshold=length_threshold,
              cluster_eps=cluster_eps if do_cluster else None,
              cluster_min=cluster_min if do_cluster else None,
              keep_noise=True,
          )

          tx, ty, _ = translation_m
          if use_ref_coords and (ref_lat is not None and ref_lon is not None):
              H = hulls[0] if hulls else np.zeros((0, 2))
              if H.shape[0] >= 3:
                  poly = transform_polygon_local_to_wgs84_ref(H, float(ref_lat), float(ref_lon))
                  return write_geojson(poly, out_path)
              else:
                  geom = Point(float(ref_lon), float(ref_lat))
                  return write_geojson(geom, out_path)

          polys = []
          for H in hulls:
              poly = transform_polygon_local_to_wgs84(H, translation_m, epsg)
              if poly and not poly.is_empty:
                  polys.append(poly)

          union_poly = unary_union(polys) if polys else Polygon()
          return write_geojson(union_poly, out_path)


      # =============================================================================
      # GLTF ROTATION
      # =============================================================================

      def rotate_gltf(in_path: str, out_path: str, axis: str = 'y', angle_deg: float = 90.0) -> str:
          """Rotate GLTF/GLB file by adding a wrapper node."""
          g = GLTF2().load(in_path)
          angle = math.radians(angle_deg)
          half = angle / 2.0
          s = math.sin(half)
          c = math.cos(half)

          qx = qy = qz = 0.0
          axis = axis.lower()
          if axis == 'x':
              qx = s
          elif axis == 'y':
              qy = s
          elif axis == 'z':
              qz = s
          else:
              raise ValueError(f"Unsupported rotation axis: {axis}")
          qw = c

          scene_index = g.scene if isinstance(g.scene, int) else 0
          scene = g.scenes[scene_index]
          original_roots = list(scene.nodes or [])

          wrapper = Node(
              name=f"RotationWrapper_{angle_deg}deg_{axis}",
              rotation=[qx, qy, qz, qw],
              translation=[0, 0, 0],
              scale=[1, 1, 1],
              children=original_roots if original_roots else None
          )

          wrapper_index = len(g.nodes)
          g.nodes.append(wrapper)
          scene.nodes = [wrapper_index]
          g.scenes[scene_index] = scene
          g.save(out_path)
          return out_path


      # =============================================================================
      # COMMAND EXECUTION HELPERS
      # =============================================================================

      def _decode_and_normalize(stdout: bytes, stderr: bytes) -> str:
          """Decode and normalize command output."""
          def decode(b: bytes) -> str:
              for enc in ("utf-16le", "utf-16", "utf-8", "cp1252"):
                  try:
                      s = b.decode(enc, errors="replace")
                      s = s.replace("\u0000", "")
                      return s
                  except Exception:
                      continue
              return b.decode(errors="replace")

          out = decode(stdout or b"")
          err = decode(stderr or b"")

          return out + "\n" + err


      def run_command(cmd: List[str], timeout_sec: int = 1800) -> Tuple[int, str]:
          """Run command and return exit code and output."""
          try:
              p = subprocess.Popen(cmd, stdout=subprocess.PIPE, stderr=subprocess.PIPE)
              try:
                  stdout, stderr = p.communicate(timeout=timeout_sec)
              except subprocess.TimeoutExpired:
                  p.kill()
                  stdout, stderr = p.communicate()
                  return 124, _decode_and_normalize(stdout, stderr) + "\n[timeout exceeded]"
              return p.returncode, _decode_and_normalize(stdout, stderr)
          except FileNotFoundError:
              return 127, f"Executable not found: {cmd[0]}"


      def run_command_to_file(cmd: List[str], logfile: str, timeout_sec: int = 1800) -> int:
          """Run command and write output to logfile."""
          code, output = run_command(cmd, timeout_sec)
          with open(logfile, 'w', encoding='utf-8', errors='replace') as lf:
              lf.write(output)
          return code


      def _safe_remove(path: Optional[str]) -> None:
          """Safely remove a file if it exists."""
          try:
              if path and os.path.isfile(path):
                  os.remove(path)
          except Exception:
              pass


      def _file_nonempty(path: str, min_bytes: int = 1) -> bool:
          """Check if file exists and is non-empty."""
          try:
              return os.path.isfile(path) and os.path.getsize(path) > min_bytes
          except Exception:
              return False


      # =============================================================================
      # DWG CONVERSION FUNCTIONS
      # =============================================================================

      def convert_dwg_with_oda(dwg_path: str, output_dir: str, oda_path: str) -> Tuple[Optional[str], str]:
          """
          Convert DWG to OBJ using ODA File Converter.

          ODA File Converter command line:
          ODAFileConverter.exe <source folder> <dest folder> <output version> <output type> [options]

          Returns: (obj_path or None, error_message)
          """
          if not os.path.isfile(oda_path):
              return None, f"ODA File Converter not found: {oda_path}"

          if not os.path.isfile(dwg_path):
              return None, f"DWG file not found: {dwg_path}"

          # Create temp directory for conversion
          temp_dir = tempfile.mkdtemp(prefix="dwg2geo_")

          try:
              # Copy DWG to temp folder (ODA works on folders)
              dwg_name = os.path.basename(dwg_path)
              base_name = os.path.splitext(dwg_name)[0]
              temp_dwg = os.path.join(temp_dir, dwg_name)
              shutil.copy2(dwg_path, temp_dwg)

              # Output folder
              temp_out = os.path.join(temp_dir, "output")
              os.makedirs(temp_out, exist_ok=True)

              # Run ODA File Converter to convert to DXF first (more compatible)
              # Then we'll use trimesh/ezdxf to convert to OBJ
              cmd = [
                  oda_path,
                  temp_dir,  # Source folder
                  temp_out,  # Destination folder
                  "ACAD2018",  # Output version
                  "DXF",  # Output type (DXF is more parseable)
                  "0",  # Recurse subdirectories: 0=no
                  "1",  # Audit: 1=yes
              ]

              code, output = run_command(cmd, timeout_sec=300)

              if code != 0:
                  return None, f"ODA conversion failed (code {code}): {output}"

              # Find output DXF file
              dxf_path = os.path.join(temp_out, base_name + ".dxf")
              if not os.path.isfile(dxf_path):
                  # Try lowercase
                  dxf_path = os.path.join(temp_out, base_name.lower() + ".dxf")

              if not os.path.isfile(dxf_path):
                  return None, f"DXF output not found after conversion"

              # Now convert DXF to OBJ using trimesh (if it can load it)
              # Or return the DXF path for further processing
              return dxf_path, ""

          except Exception as e:
              return None, f"Conversion error: {str(e)}"


      def convert_dxf_to_glb(dxf_path: str, output_glb: str) -> Tuple[bool, str]:
          """
          Convert DXF to GLB using trimesh.

          Note: trimesh has limited DXF support - mainly for 2D/simple 3D entities.
          """
          try:
              # Try loading with trimesh
              scene = trimesh.load(dxf_path)

              if isinstance(scene, trimesh.Scene):
                  if len(scene.geometry) == 0:
                      return False, "No geometry found in DXF file"
              elif isinstance(scene, trimesh.Trimesh):
                  if len(scene.vertices) == 0:
                      return False, "No vertices found in DXF file"
              else:
                  return False, f"Unexpected geometry type: {type(scene)}"

              # Export to GLB
              scene.export(output_glb, file_type='glb')

              if os.path.isfile(output_glb) and os.path.getsize(output_glb) > 100:
                  return True, ""
              else:
                  return False, "GLB file not created or empty"

          except Exception as e:
              return False, f"DXF to GLB conversion failed: {str(e)}"


      def convert_obj_to_glb(obj_path: str, output_glb: str) -> Tuple[bool, str]:
          """Convert OBJ to GLB using trimesh."""
          try:
              scene = trimesh.load(obj_path)
              scene.export(output_glb, file_type='glb')

              if os.path.isfile(output_glb) and os.path.getsize(output_glb) > 100:
                  return True, ""
              else:
                  return False, "GLB file not created or empty"

          except Exception as e:
              return False, f"OBJ to GLB conversion failed: {str(e)}"


      def build_gltfpack_command(cfg: PipelineConfig, in_glb: str, out_glb: str) -> List[str]:
          """Build gltfpack command."""
          return [
              cfg.gltfpack_path or 'gltfpack',
              '-i', in_glb,
              '-o', out_glb,
              '-vp', '16', '-mm', '-cc'
          ]


      # =============================================================================
      # FME GEOMETRY TO MESH CONVERSION
      # =============================================================================

      def _extract_coords_from_fme_point(point) -> Optional[Tuple[float, float, float]]:
          """Extract X,Y,Z coordinates from an FME point or coordinate object."""
          try:
              if point is None:
                  return None

              # FMEPoint.getXYZ() returns (x, y, z) tuple
              if hasattr(point, 'getXYZ'):
                  xyz = point.getXYZ()
                  if xyz and len(xyz) >= 2:
                      return (float(xyz[0]), float(xyz[1]), float(xyz[2]) if len(xyz) > 2 else 0.0)

              # FMEPoint has getX(), getY(), getZ() methods
              if hasattr(point, 'getX') and hasattr(point, 'getY'):
                  x = point.getX()
                  y = point.getY()
                  z = point.getZ() if hasattr(point, 'getZ') else 0.0
                  if x is not None and y is not None:
                      return (float(x), float(y), float(z) if z is not None else 0.0)

              # Direct tuple/list - common for FME coordinate returns
              if isinstance(point, (list, tuple)):
                  if len(point) >= 2:
                      x, y = float(point[0]), float(point[1])
                      z = float(point[2]) if len(point) > 2 else 0.0
                      return (x, y, z)

              # FMECoordinate or similar - try x, y, z attributes
              if hasattr(point, 'x') and hasattr(point, 'y'):
                  x = point.x
                  y = point.y
                  z = point.z if hasattr(point, 'z') else 0.0
                  if x is not None and y is not None:
                      return (float(x), float(y), float(z) if z is not None else 0.0)

              # Try indexing as fallback
              try:
                  if len(point) >= 2:
                      return (float(point[0]), float(point[1]), float(point[2]) if len(point) > 2 else 0.0)
              except (TypeError, IndexError):
                  pass

          except Exception as e:
              # Uncomment for debugging:
              # print(f"[DWG2Geo] Point extraction error: {e}, type={type(point)}")
              pass
          return None


      def _extract_mesh_from_fme_mesh(mesh_geom) -> Tuple[List[List[float]], List[List[int]]]:
          """
          Extract vertices and faces from FMEMesh geometry.

          FMEMesh is the native mesh type in FME - commonly produced by 3D formats.
          """
          vertices = []
          faces = []

          try:
              # Get number of vertices
              if hasattr(mesh_geom, 'numVertices'):
                  num_verts = mesh_geom.numVertices()
                  for i in range(num_verts):
                      coords = mesh_geom.getVertexAsPoint(i) if hasattr(mesh_geom, 'getVertexAsPoint') else None
                      if coords is None and hasattr(mesh_geom, 'getVertexAt'):
                          coords = mesh_geom.getVertexAt(i)
                      if coords:
                          pt = _extract_coords_from_fme_point(coords)
                          if pt:
                              vertices.append(list(pt))

              # Get faces/triangles
              if hasattr(mesh_geom, 'numFaces'):
                  num_faces = mesh_geom.numFaces()
                  for i in range(num_faces):
                      face_verts = mesh_geom.getFaceAsPointArray(i) if hasattr(mesh_geom, 'getFaceAsPointArray') else None

                      if face_verts is None and hasattr(mesh_geom, 'getFaceVertexIndices'):
                          # Get vertex indices directly
                          indices = mesh_geom.getFaceVertexIndices(i)
                          if indices and len(indices) >= 3:
                              # Triangulate if needed
                              for j in range(1, len(indices) - 1):
                                  faces.append([indices[0], indices[j], indices[j + 1]])
                      elif face_verts:
                          # Face defined by points - need to find/create vertex indices
                          face_indices = []
                          for pt in face_verts:
                              pt_coords = _extract_coords_from_fme_point(pt)
                              if pt_coords:
                                  # Find matching vertex or add new
                                  found = False
                                  for vi, v in enumerate(vertices):
                                      if abs(v[0] - pt_coords[0]) < 1e-9 and abs(v[1] - pt_coords[1]) < 1e-9 and abs(v[2] - pt_coords[2]) < 1e-9:
                                          face_indices.append(vi)
                                          found = True
                                          break
                                  if not found:
                                      face_indices.append(len(vertices))
                                      vertices.append(list(pt_coords))

                          if len(face_indices) >= 3:
                              # Triangulate
                              for j in range(1, len(face_indices) - 1):
                                  faces.append([face_indices[0], face_indices[j], face_indices[j + 1]])
          except Exception as e:
              print(f"[DWG2Geo] FMEMesh extraction error: {e}")

          return vertices, faces


      def _extract_mesh_from_fme_surface(surface_geom) -> Tuple[List[List[float]], List[List[int]]]:
          """
          Extract vertices and faces from FMESurface/FMEFace geometry.

          Handles triangulation of polygon surfaces.
          """
          vertices = []
          faces = []

          try:
              # Try to get triangulated version first
              if hasattr(surface_geom, 'getAsTriangles'):
                  triangles = surface_geom.getAsTriangles()
                  if triangles:
                      return _extract_mesh_from_fme_mesh(triangles)

              # Get boundary of surface
              boundary = None
              if hasattr(surface_geom, 'getBoundaryAsCurve'):
                  boundary = surface_geom.getBoundaryAsCurve()
              elif hasattr(surface_geom, 'getOuterBoundaryAsCurve'):
                  boundary = surface_geom.getOuterBoundaryAsCurve()

              if boundary and hasattr(boundary, 'getCoordinates'):
                  coords = boundary.getCoordinates()
                  if coords:
                      for c in coords:
                          pt = _extract_coords_from_fme_point(c)
                          if pt:
                              vertices.append(list(pt))

                      # Triangulate as fan from first vertex
                      if len(vertices) >= 3:
                          for i in range(1, len(vertices) - 1):
                              faces.append([0, i, i + 1])
          except Exception as e:
              print(f"[DWG2Geo] FMESurface extraction error: {e}")

          return vertices, faces


      def _extract_mesh_from_fme_solid(solid_geom) -> Tuple[List[List[float]], List[List[int]]]:
          """
          Extract vertices and faces from FMESolid/FMEBRepSolid geometry.

          Processes all faces of the solid boundary.
          """
          all_vertices = []
          all_faces = []

          try:
              # Try to get as mesh directly
              if hasattr(solid_geom, 'getAsMesh'):
                  mesh = solid_geom.getAsMesh()
                  if mesh:
                      return _extract_mesh_from_fme_mesh(mesh)

              # Get outer shell/boundary
              outer_surface = None
              if hasattr(solid_geom, 'getOuterSurface'):
                  outer_surface = solid_geom.getOuterSurface()
              elif hasattr(solid_geom, 'getBoundaryAsMultiSurface'):
                  outer_surface = solid_geom.getBoundaryAsMultiSurface()

              if outer_surface:
                  # Process as multi-surface
                  verts, faces = _extract_mesh_from_fme_multi(outer_surface)
                  all_vertices.extend(verts)
                  all_faces.extend(faces)
          except Exception as e:
              print(f"[DWG2Geo] FMESolid extraction error: {e}")

          return all_vertices, all_faces


      def _extract_mesh_from_fme_multi(multi_geom) -> Tuple[List[List[float]], List[List[int]]]:
          """
          Extract vertices and faces from FMEMultiSurface, FMECompositeSurface, or FMEAggregate.
          """
          all_vertices = []
          all_faces = []
          vertex_offset = 0

          try:
              num_parts = 0
              if hasattr(multi_geom, 'numParts'):
                  num_parts = multi_geom.numParts()
              elif hasattr(multi_geom, 'numGeometries'):
                  num_parts = multi_geom.numGeometries()

              for i in range(num_parts):
                  part = None
                  if hasattr(multi_geom, 'getPartAt'):
                      part = multi_geom.getPartAt(i)
                  elif hasattr(multi_geom, 'getGeometryAt'):
                      part = multi_geom.getGeometryAt(i)

                  if part:
                      mesh = fme_geometry_to_trimesh(part)
                      if mesh:
                          all_vertices.extend(mesh.vertices.tolist())
                          # Offset face indices
                          for face in mesh.faces:
                              all_faces.append([f + vertex_offset for f in face])
                          vertex_offset += len(mesh.vertices)
          except Exception as e:
              print(f"[DWG2Geo] Multi-geometry extraction error: {e}")

          return all_vertices, all_faces


      def fme_geometry_to_trimesh(geometry: fmeobjects.FMEGeometry) -> Optional[trimesh.Trimesh]:
          """
          Convert FME 3D geometry to trimesh mesh.

          Supports: FMEMesh, FMESolid, FMEBRepSolid, FMESurface, FMEFace,
                    FMEMultiSurface, FMECompositeSurface, FMEAggregate, FMEMultiSolid

          Note: This function only processes 3D geometry types. 2D geometry types
          (FMEArc, FMELine, FMEPath, etc.) will be skipped and return None.

          Args:
              geometry: FME 3D geometry object

          Returns:
              trimesh.Trimesh or None if geometry cannot be converted
          """
          vertices = []
          faces = []

          try:
              if geometry is None:
                  return None

              # Get geometry type name
              geom_type = ""
              if hasattr(geometry, 'typeName'):
                  geom_type = geometry.typeName()
              else:
                  geom_type = type(geometry).__name__

              # Handle FMEMesh directly
              if 'Mesh' in geom_type and 'Multi' not in geom_type:
                  vertices, faces = _extract_mesh_from_fme_mesh(geometry)

              # Handle solids (FMESolid, FMEBRepSolid, etc.)
              elif 'Solid' in geom_type and 'Multi' not in geom_type:
                  vertices, faces = _extract_mesh_from_fme_solid(geometry)

              # Handle surfaces (FMESurface, FMEFace, etc.)
              elif 'Surface' in geom_type and 'Multi' not in geom_type and 'Composite' not in geom_type:
                  vertices, faces = _extract_mesh_from_fme_surface(geometry)
              elif 'Face' in geom_type:
                  vertices, faces = _extract_mesh_from_fme_surface(geometry)

              # Handle multi/composite geometries
              elif any(x in geom_type for x in ['Multi', 'Composite', 'Aggregate', 'Collection']):
                  vertices, faces = _extract_mesh_from_fme_multi(geometry)

              # Try generic approach - get as triangulated mesh
              else:
                  # Many FME geometries support getAsTriangles or similar
                  if hasattr(geometry, 'getTriangulatedGeometry'):
                      triangulated = geometry.getTriangulatedGeometry()
                      if triangulated:
                          return fme_geometry_to_trimesh(triangulated)

                  if hasattr(geometry, 'getAsMesh'):
                      mesh = geometry.getAsMesh()
                      if mesh:
                          vertices, faces = _extract_mesh_from_fme_mesh(mesh)

                  # Last resort - try to extract any coordinates
                  if not vertices and hasattr(geometry, 'getAllCoordinates'):
                      coords = geometry.getAllCoordinates()
                      if coords:
                          for c in coords:
                              pt = _extract_coords_from_fme_point(c)
                              if pt:
                                  vertices.append(list(pt))

              # Create trimesh if we have valid data
              if vertices and faces:
                  try:
                      mesh = trimesh.Trimesh(
                          vertices=np.array(vertices, dtype=np.float64),
                          faces=np.array(faces, dtype=np.int64)
                      )
                      # Validate mesh
                      if len(mesh.vertices) >= 3 and len(mesh.faces) >= 1:
                          return mesh
                  except Exception as e:
                      print(f"[DWG2Geo] Trimesh creation error: {e}")

              # If we only have vertices (point cloud), try convex hull
              elif vertices and len(vertices) >= 4:
                  try:
                      from scipy.spatial import ConvexHull
                      verts = np.array(vertices, dtype=np.float64)
                      hull = ConvexHull(verts)
                      return trimesh.Trimesh(vertices=verts, faces=hull.simplices)
                  except Exception as e:
                      print(f"[DWG2Geo] Convex hull creation failed: {e}")

              return None

          except Exception as e:
              print(f"[DWG2Geo] Geometry conversion error: {e}")
              import traceback
              traceback.print_exc()
              return None


      def combine_meshes(meshes: List[trimesh.Trimesh]) -> Optional[trimesh.Trimesh]:
          """Combine multiple trimesh objects into one."""
          if not meshes:
              return None

          if len(meshes) == 1:
              return meshes[0]

          try:
              combined = trimesh.util.concatenate(meshes)
              return combined
          except Exception as e:
              print(f"[DWG2Geo] Mesh combination error: {e}")
              return meshes[0] if meshes else None


      # =============================================================================
      # MAIN PIPELINE
      # =============================================================================

      def process_dwg_file(dwg_path: str, cfg: PipelineConfig) -> Dict[str, Any]:
          """
          Process DWG file using external converter (ODA File Converter).

          Args:
              dwg_path: Path to DWG/DWF file
              cfg: Pipeline configuration

          Returns:
              Dictionary with processing results
          """
          result: Dict[str, Any] = {"warnings": [], "steps": []}

          if not os.path.isfile(dwg_path):
              raise FileNotFoundError(f"DWG file not found: {dwg_path}")

          # Determine output directory
          output_dir = cfg.output_dir or os.path.dirname(dwg_path)
          if not output_dir:
              output_dir = os.getcwd()
          os.makedirs(output_dir, exist_ok=True)

          print(f"[DWG2Geo] Processing DWG file: {dwg_path}")
          print(f"[DWG2Geo] Output directory: {output_dir}")

          # Output naming
          base_name = os.path.splitext(os.path.basename(dwg_path))[0]
          raw_glb = os.path.join(output_dir, f"{base_name}_raw.glb")
          rotated_glb = os.path.join(output_dir, f"{base_name}_raw_rot.glb")
          packed_glb = os.path.join(output_dir, f"{base_name}_raw_rot_comp.glb")
          final_glb = os.path.join(output_dir, f"{base_name}.glb")
          plan_geojson = os.path.join(output_dir, f"{base_name}_planpolygon.geojson")
          meta_json = os.path.join(output_dir, f"{base_name}.json")

          # Pre-run cleanup
          for p in (raw_glb, rotated_glb, packed_glb, final_glb, plan_geojson, meta_json):
              _safe_remove(p)

          # Georeferencing - for DWG we rely on provided ref coordinates or EPSG
          epsg = cfg.source_epsg or cfg.fallback_epsg
          lat, lon = cfg.ref_lat, cfg.ref_lon

          # Try to transform centroid if no ref coords provided
          translation_m = (0.0, 0.0, cfg.ref_elevation)
          use_ref_coords = False

          if lat is not None and lon is not None:
              lat, lon = validate_latlon(lat, lon)
              use_ref_coords = True
          else:
              result['warnings'].append('No reference coordinates provided; using EPSG origin.')

          # 1. Convert DWG to GLB
          if cfg.oda_converter_path:
              print(f"[DWG2Geo] Converting DWG with ODA File Converter")

              dxf_path, error = convert_dwg_with_oda(dwg_path, output_dir, cfg.oda_converter_path)

              if dxf_path:
                  success, error = convert_dxf_to_glb(dxf_path, raw_glb)
                  if not success:
                      result['warnings'].append(f'DXF to GLB conversion failed: {error}')
              else:
                  result['warnings'].append(f'ODA conversion failed: {error}')

                  # Try direct trimesh load as fallback
                  print("[DWG2Geo] Trying direct trimesh load...")
                  try:
                      scene = trimesh.load(dwg_path)
                      scene.export(raw_glb, file_type='glb')
                      if _file_nonempty(raw_glb, 100):
                          print("[DWG2Geo] Direct trimesh load succeeded")
                      else:
                          result['warnings'].append('Direct trimesh load produced empty file')
                  except Exception as e:
                      result['warnings'].append(f'Direct trimesh load failed: {e}')
          else:
              result['warnings'].append('ODA File Converter not configured; trying direct trimesh load.')

              # Try direct trimesh load
              try:
                  scene = trimesh.load(dwg_path)
                  scene.export(raw_glb, file_type='glb')
                  if not _file_nonempty(raw_glb, 100):
                      result['warnings'].append('Direct load produced empty GLB')
              except Exception as e:
                  result['warnings'].append(f'Direct load failed: {e}')

          # 2. Plan polygon (only if raw_glb exists)
          if os.path.isfile(raw_glb):
              try:
                  generate_plan_geojson(
                      raw_glb,
                      plan_geojson,
                      translation_m,
                      epsg,
                      concavity=cfg.hull_concavity,
                      length_threshold=cfg.hull_length_threshold,
                      grid=cfg.hull_grid,
                      stride=cfg.hull_stride,
                      mirror_xy=True,
                      cluster_eps=cfg.cluster_eps,
                      cluster_min=cfg.cluster_min,
                      cluster_point_threshold=cfg.cluster_point_threshold,
                      ref_lat=lat,
                      ref_lon=lon,
                      use_ref_coords=use_ref_coords,
                  )
              except Exception as e:
                  result['warnings'].append(f'Failed to generate plan polygon: {e}')
          else:
              result['warnings'].append('Raw GLB missing; skipping plan polygon generation.')

          # 3. Rotation
          if os.path.isfile(raw_glb):
              try:
                  rotate_gltf(raw_glb, rotated_glb, axis=cfg.rotation_axis, angle_deg=cfg.rotation_deg)
              except Exception as e:
                  result['warnings'].append(f'Rotation failed: {e}')
          else:
              result['warnings'].append('Raw GLB missing; skipping rotation.')

          # 4. Packing (optional)
          if os.path.isfile(rotated_glb) and cfg.gltfpack_path:
              cmd_pack = build_gltfpack_command(cfg, rotated_glb, packed_glb)
              code = run_command_to_file(cmd_pack, os.path.join(output_dir, f"{base_name}_gltfpack.log"))
              if code != 0:
                  result['warnings'].append('gltfpack failed.')
          elif not cfg.gltfpack_path:
              result['warnings'].append('gltfpack not configured; skipping compression.')
          elif not os.path.isfile(rotated_glb):
              result['warnings'].append('Rotated GLB missing; packing step skipped.')

          # Determine final GLB and optionally clean intermediates
          final_path = None
          if os.path.isfile(packed_glb):
              final_path = packed_glb
          elif os.path.isfile(rotated_glb):
              final_path = rotated_glb
          elif os.path.isfile(raw_glb):
              final_path = raw_glb

          keep_intermediate = cfg.keep_intermediate_files
          if final_path:
              if not keep_intermediate and final_path != final_glb:
                  try:
                      _safe_remove(final_glb)
                      shutil.move(final_path, final_glb)
                      final_path = final_glb
                  except Exception as e:
                      result['warnings'].append(f'Failed to rename final GLB: {e}')
              if not keep_intermediate:
                  for p in (raw_glb, rotated_glb, packed_glb):
                      if p != final_path:
                          _safe_remove(p)

          # 5. Metadata JSON
          height_val = cfg.ref_elevation

          gltf_entry = {
              'url': os.path.basename(final_path) if final_path and os.path.isfile(final_path) else None,
              'lat': lat if (lat is not None) else 0,
              'lng': lon if (lon is not None) else 0,
              'height': height_val,
              'heightReference': 'NONE',
              'rotHeading': 0,
              'animation': False
          }

          meta = {
              'gltf': [gltf_entry],
              'epsg': epsg,
              'source_file': os.path.basename(dwg_path),
              'warnings': result['warnings']
          }

          try:
              with open(meta_json, 'w', encoding='utf-8') as f:
                  json.dump(meta, f, indent=2)
          except Exception as e:
              result['warnings'].append(f'Failed writing metadata JSON: {e}')

          result['outputs'] = {
              'raw_glb': raw_glb if os.path.isfile(raw_glb) else None,
              'rotated_glb': rotated_glb if os.path.isfile(rotated_glb) else None,
              'packed_glb': packed_glb if os.path.isfile(packed_glb) else None,
              'final_glb': final_path if (final_path and os.path.isfile(final_path)) else None,
              'plan_geojson': plan_geojson if os.path.isfile(plan_geojson) else None,
              'meta_json': meta_json if os.path.isfile(meta_json) else None,
          }
          result['epsg'] = epsg
          result['lat'] = lat
          result['lon'] = lon
          result['elevation'] = height_val

          return result


      def process_fme_geometries(geometries: List[fmeobjects.FMEGeometry], base_name: str,
                                 cfg: PipelineConfig) -> Dict[str, Any]:
          """
          Process FME geometries (from DWG reader) into GLB.

          Args:
              geometries: List of FME geometry objects
              base_name: Base name for output files
              cfg: Pipeline configuration

          Returns:
              Dictionary with processing results
          """
          result: Dict[str, Any] = {"warnings": [], "steps": []}

          # Determine output directory
          output_dir = cfg.output_dir
          if not output_dir:
              output_dir = os.getcwd()
          os.makedirs(output_dir, exist_ok=True)

          print(f"[DWG2Geo] Processing {len(geometries)} FME geometries")
          print(f"[DWG2Geo] Output directory: {output_dir}")

          # Output naming
          raw_glb = os.path.join(output_dir, f"{base_name}_raw.glb")
          rotated_glb = os.path.join(output_dir, f"{base_name}_raw_rot.glb")
          packed_glb = os.path.join(output_dir, f"{base_name}_raw_rot_comp.glb")
          final_glb = os.path.join(output_dir, f"{base_name}.glb")
          plan_geojson = os.path.join(output_dir, f"{base_name}_planpolygon.geojson")
          meta_json = os.path.join(output_dir, f"{base_name}.json")
          pack_log = os.path.join(output_dir, f"{base_name}_gltfpack.log")

          # Pre-run cleanup
          for p in (raw_glb, rotated_glb, packed_glb, final_glb, plan_geojson, meta_json, pack_log):
              _safe_remove(p)

          # Convert FME 3D geometries to trimesh
          print(f"[DWG2Geo] Converting {len(geometries)} 3D geometries to mesh...")
          if cfg.merge_vertices:
              print(f"[DWG2Geo] Vertex merging enabled (tolerance={cfg.merge_tolerance}m)")
          if cfg.simplify_mesh:
              print(f"[DWG2Geo] Mesh simplification enabled (ratio={cfg.simplify_ratio})")
          meshes = []
          conversion_errors = 0
          geom_type_counts = {}

          for i, geom in enumerate(geometries):
              # Track geometry types for debugging
              geom_type = geom.typeName() if hasattr(geom, 'typeName') else type(geom).__name__
              geom_type_counts[geom_type] = geom_type_counts.get(geom_type, 0) + 1

              mesh = fme_geometry_to_trimesh(geom)
              if mesh:
                  meshes.append(mesh)
                  # Log progress every 1000 geometries or for first 3
                  if i < 3 or (i + 1) % 1000 == 0:
                      print(f"[DWG2Geo] Progress: {i+1}/{len(geometries)} ({len(meshes)} converted)")
              else:
                  conversion_errors += 1

          # Log summary of geometry types
          print(f"[DWG2Geo] Geometry type summary:")
          for gtype, count in sorted(geom_type_counts.items()):
              print(f"[DWG2Geo]   - {gtype}: {count}")

          if conversion_errors > 0:
              result['warnings'].append(f'{conversion_errors} geometries could not be converted to mesh')

          print(f"[DWG2Geo] Successfully converted {len(meshes)} of {len(geometries)} geometries")

          if not meshes:
              warning_msg = f'No valid 3D geometry found in {len(geometries)} input features. Ensure DWG contains 3D geometry (Solids, Surfaces, Meshes).'
              result['warnings'].append(warning_msg)
              print(f"[DWG2Geo] ERROR: {warning_msg}")
              print(f"[DWG2Geo] TIP: Check FME log for specific geometry extraction errors.")

              # Still write a metadata JSON with the error info
              error_meta = {
                  'error': warning_msg,
                  'geometry_count': len(geometries),
                  'conversion_errors': conversion_errors,
                  'warnings': result['warnings']
              }
              try:
                  with open(meta_json, 'w', encoding='utf-8') as f:
                      json.dump(error_meta, f, indent=2)
                  result['outputs'] = {'meta_json': meta_json}
              except:
                  result['outputs'] = {}
              return result

          # Combine and export
          print(f"[DWG2Geo] Combining {len(meshes)} meshes...")
          combined = combine_meshes(meshes)
          if combined:
              original_verts = len(combined.vertices)
              original_faces = len(combined.faces)
              print(f"[DWG2Geo] Combined mesh: {original_verts} vertices, {original_faces} faces")

              # Merge close vertices to reduce duplicates
              if cfg.merge_vertices and cfg.merge_tolerance > 0:
                  try:
                      combined.merge_vertices(merge_tex=True, merge_norm=True)
                      print(f"[DWG2Geo] After merge_vertices: {len(combined.vertices)} vertices (was {original_verts})")
                  except Exception as e:
                      print(f"[DWG2Geo] Vertex merge failed: {e}")

              # Optional mesh simplification
              if cfg.simplify_mesh and cfg.simplify_ratio < 1.0:
                  try:
                      target_faces = int(len(combined.faces) * cfg.simplify_ratio)
                      if target_faces > 100:
                          simplified = combined.simplify_quadric_decimation(target_faces)
                          print(f"[DWG2Geo] Simplified: {len(simplified.faces)} faces (was {len(combined.faces)})")
                          combined = simplified
                  except Exception as e:
                      print(f"[DWG2Geo] Mesh simplification failed (scipy may be required): {e}")

              combined.export(raw_glb, file_type='glb')
              if not _file_nonempty(raw_glb, 100):
                  result['warnings'].append('Raw GLB export produced empty or invalid file')
                  result['outputs'] = {}
                  return result
              print(f"[DWG2Geo] Exported raw GLB: {raw_glb} ({os.path.getsize(raw_glb) / 1024:.1f} KB)")
          else:
              result['warnings'].append('Failed to combine meshes')
              result['outputs'] = {}
              return result

          # Georeferencing
          epsg = cfg.source_epsg or cfg.fallback_epsg
          lat, lon = cfg.ref_lat, cfg.ref_lon
          translation_m = (0.0, 0.0, cfg.ref_elevation)
          use_ref_coords = lat is not None and lon is not None

          if lat is not None and lon is not None:
              lat, lon = validate_latlon(lat, lon)

          # Generate plan polygon
          if os.path.isfile(raw_glb):
              try:
                  generate_plan_geojson(
                      raw_glb,
                      plan_geojson,
                      translation_m,
                      epsg,
                      concavity=cfg.hull_concavity,
                      ref_lat=lat,
                      ref_lon=lon,
                      use_ref_coords=use_ref_coords,
                  )
                  print(f"[DWG2Geo] Generated plan polygon: {plan_geojson}")
              except Exception as e:
                  result['warnings'].append(f'Failed to generate plan polygon: {e}')

          # Rotation
          if os.path.isfile(raw_glb):
              try:
                  rotate_gltf(raw_glb, rotated_glb, axis=cfg.rotation_axis, angle_deg=cfg.rotation_deg)
                  print(f"[DWG2Geo] Rotated GLB: {rotated_glb}")
              except Exception as e:
                  result['warnings'].append(f'Rotation failed: {e}')

          # Packing (optional gltfpack compression)
          if os.path.isfile(rotated_glb) and cfg.gltfpack_path:
              cmd_pack = build_gltfpack_command(cfg, rotated_glb, packed_glb)
              code = run_command_to_file(cmd_pack, pack_log)
              if code == 0 and _file_nonempty(packed_glb, 100):
                  print(f"[DWG2Geo] Compressed GLB: {packed_glb}")
              else:
                  result['warnings'].append('gltfpack compression failed; using uncompressed GLB.')
          elif not cfg.gltfpack_path:
              result['warnings'].append('gltfpack not configured; skipping compression.')

          # Determine final GLB
          final_path = None
          if os.path.isfile(packed_glb):
              final_path = packed_glb
          elif os.path.isfile(rotated_glb):
              final_path = rotated_glb
          elif os.path.isfile(raw_glb):
              final_path = raw_glb

          if final_path and not cfg.keep_intermediate_files and final_path != final_glb:
              try:
                  _safe_remove(final_glb)
                  shutil.move(final_path, final_glb)
                  final_path = final_glb
              except Exception as e:
                  result['warnings'].append(f'Failed to rename final GLB: {e}')

          # Clean up intermediate files
          if not cfg.keep_intermediate_files:
              for p in (raw_glb, rotated_glb, packed_glb, pack_log):
                  if p != final_path:
                      _safe_remove(p)

          print(f"[DWG2Geo] Final GLB: {final_path}")

          # Metadata JSON
          gltf_entry = {
              'url': os.path.basename(final_path) if final_path else None,
              'lat': lat if lat else 0,
              'lng': lon if lon else 0,
              'height': cfg.ref_elevation,
              'heightReference': 'NONE',
              'rotHeading': 0,
              'animation': False
          }

          meta = {
              'gltf': [gltf_entry],
              'epsg': epsg,
              'geometry_count': len(geometries),
              'mesh_count': len(meshes),
              'warnings': result['warnings']
          }

          try:
              with open(meta_json, 'w', encoding='utf-8') as f:
                  json.dump(meta, f, indent=2)
              print(f"[DWG2Geo] Metadata JSON: {meta_json}")
          except Exception as e:
              result['warnings'].append(f'Failed writing metadata JSON: {e}')

          result['outputs'] = {
              'raw_glb': raw_glb if os.path.isfile(raw_glb) else None,
              'rotated_glb': rotated_glb if os.path.isfile(rotated_glb) else None,
              'packed_glb': packed_glb if os.path.isfile(packed_glb) else None,
              'final_glb': final_path if (final_path and os.path.isfile(final_path)) else None,
              'plan_geojson': plan_geojson if os.path.isfile(plan_geojson) else None,
              'meta_json': meta_json if os.path.isfile(meta_json) else None,
          }
          result['epsg'] = epsg
          result['lat'] = lat
          result['lon'] = lon
          result['elevation'] = cfg.ref_elevation

          return result


      # =============================================================================
      # FME PYTHONCALLER CLASSES
      # =============================================================================

      class FileProcessor(BaseTransformer):
          """
          FME PythonCaller class for DWG/DWF to GLB + GeoJSON processing.

          This processes DWG/DWF files using external converters (ODA File Converter).

          Usage:
          1. Use Directory/File Reader to list DWG files
          2. Set 'Class to Process Features' to 'FileProcessor'
          3. Set 'ODAConverter' attribute to path of ODAFileConverter.exe
          4. Optional: Set gltfpack, ref_lat, ref_lon, output_dir, etc.
          """

          def __init__(self):
              """Initialize the FileProcessor."""
              super().__init__()
              self._error_count = 0
              self._success_count = 0

          def has_support_for(self, support_type: int):
              """FME support query."""
              return support_type == fmeobjects.FME_SUPPORT_FEATURE_TABLE_SHIM

          def input(self, feature: fmeobjects.FMEFeature):
              """Process each incoming feature."""
              try:
                  # Get DWG path from feature
                  dwg_path = fme.macroValues['filecopy_source_dataset']

                  print(f"[DWG2Geo] Attempting to read DWG path from 'filecopy_source_dataset': {dwg_path}")

                  if not dwg_path:
                      dwg_path = feature.getAttribute('dwg_path')
                      print(f"[DWG2Geo] Fallback - reading from 'dwg_path': {dwg_path}")

                  if not dwg_path:
                      all_attrs = feature.getAllAttributeNames()
                      print(f"[DWG2Geo] ERROR: No DWG path found. Available attributes: {list(all_attrs)}")
                      self.reject_feature(feature, "MISSING_DWG_PATH",
                                         "Feature missing required 'filecopy_source_dataset' or 'dwg_path' attribute")
                      return

                  if not os.path.isfile(dwg_path):
                      print(f"[DWG2Geo] ERROR: DWG file does not exist: {dwg_path}")
                      self.reject_feature(feature, "FILE_NOT_FOUND", f"DWG file not found: {dwg_path}")
                      return

                  print(f"[DWG2Geo] Processing DWG file: {dwg_path}")

                  # Build configuration from feature attributes
                  cfg = config_from_feature(feature)

                  # Process the DWG file
                  result = process_dwg_file(dwg_path, cfg)

                  # Set output attributes
                  feature.setAttribute('process_status', 'success')
                  feature.setAttribute('warnings', json.dumps(result.get('warnings', [])))

                  outputs = result.get('outputs', {})
                  feature.setAttribute('final_glb', outputs.get('final_glb', ''))
                  feature.setAttribute('plan_geojson', outputs.get('plan_geojson', ''))
                  feature.setAttribute('meta_json', outputs.get('meta_json', ''))

                  feature.setAttribute('lat', result.get('lat'))
                  feature.setAttribute('lon', result.get('lon'))
                  feature.setAttribute('elevation', result.get('elevation', 0))
                  feature.setAttribute('epsg', result.get('epsg'))

                  self._success_count += 1
                  self.pyoutput(feature, output_tag="PYOUTPUT")

              except FileNotFoundError as e:
                  self.reject_feature(feature, "FILE_NOT_FOUND", str(e))
                  self._error_count += 1

              except Exception as e:
                  self.reject_feature(feature, "PROCESSING_ERROR", str(e))
                  self._error_count += 1

          def close(self):
              """Called after all features have been processed."""
              print(f"DWG2Geo Processing complete: {self._success_count} success, {self._error_count} errors")

          def reject_feature(self, feature: fmeobjects.FMEFeature, code: str, message: str):
              """Output a feature to the <Rejected> port with error details."""
              feature.setAttribute("fme_rejection_code", code)
              feature.setAttribute("fme_rejection_message", message)
              feature.setAttribute("process_status", "error")
              self.pyoutput(feature, output_tag="<Rejected>")


      class GeometryProcessor(BaseTransformer):
          """
          FME PythonCaller class for processing FME 3D geometry to GLB.

          This collects 3D geometry from FME's DWG reader and converts to GLB.

          Usage:
          1. Use DWG/DWF Reader to read file
          2. Filter to 3D geometry (Solids, Surfaces, Meshes, etc.)
          3. Set 'Class to Process Features' to 'GeometryProcessor'
          4. Optional: Set group-by on autocad_layer or fme_basename to batch geometries

          Supported Input Attributes:
          - fme_basename, dwg_source_dataset, autocad_entity_name: For naming output
          - coord_sys, autocad_coord_sys: For coordinate system detection
          - ref_lat, ref_lon, ref_elevation: For manual georeferencing
          - output_dir: Output directory for GLB files
          """

          def __init__(self):
              """Initialize the GeometryProcessor."""
              super().__init__()
              self._features = []  # Store cloned features instead of geometries
              self._base_name = "dwg_model"
              self._cfg = None
              self._first_feature = None
              self._error_count = 0
              self._success_count = 0
              self._bounds_min = [float('inf'), float('inf'), float('inf')]
              self._bounds_max = [float('-inf'), float('-inf'), float('-inf')]
              self._detected_epsg = None
              self._centroid = None

          def has_support_for(self, support_type: int):
              """FME support query."""
              return support_type == fmeobjects.FME_SUPPORT_FEATURE_TABLE_SHIM

          def _update_bounds_from_geometry(self, geom):
              """Update bounding box from geometry coordinates."""
              try:
                  # Try to get bounding box from FME
                  if hasattr(geom, 'boundingBox'):
                      bbox = geom.boundingBox()
                      if bbox and len(bbox) >= 4:
                          # bbox is (minx, miny, maxx, maxy) or (minx, miny, minz, maxx, maxy, maxz)
                          minx, miny = float(bbox[0]), float(bbox[1])
                          if len(bbox) == 4:
                              maxx, maxy = float(bbox[2]), float(bbox[3])
                              self._bounds_min[0] = min(self._bounds_min[0], minx)
                              self._bounds_min[1] = min(self._bounds_min[1], miny)
                              self._bounds_max[0] = max(self._bounds_max[0], maxx)
                              self._bounds_max[1] = max(self._bounds_max[1], maxy)
                          elif len(bbox) >= 6:
                              minz = float(bbox[2])
                              maxx, maxy, maxz = float(bbox[3]), float(bbox[4]), float(bbox[5])
                              self._bounds_min[0] = min(self._bounds_min[0], minx)
                              self._bounds_min[1] = min(self._bounds_min[1], miny)
                              self._bounds_min[2] = min(self._bounds_min[2], minz)
                              self._bounds_max[0] = max(self._bounds_max[0], maxx)
                              self._bounds_max[1] = max(self._bounds_max[1], maxy)
                              self._bounds_max[2] = max(self._bounds_max[2], maxz)

                  # Also try getAllCoordinates for more accuracy
                  if hasattr(geom, 'getAllCoordinates'):
                      coords = geom.getAllCoordinates()
                      if coords:
                          for c in coords:
                              if c and len(c) >= 2:
                                  x, y = float(c[0]), float(c[1])
                                  self._bounds_min[0] = min(self._bounds_min[0], x)
                                  self._bounds_min[1] = min(self._bounds_min[1], y)
                                  self._bounds_max[0] = max(self._bounds_max[0], x)
                                  self._bounds_max[1] = max(self._bounds_max[1], y)
                                  if len(c) > 2:
                                      z = float(c[2])
                                      self._bounds_min[2] = min(self._bounds_min[2], z)
                                      self._bounds_max[2] = max(self._bounds_max[2], z)
              except Exception as e:
                  print(f"[DWG2Geo] Bounds calculation error: {e}")

          def _detect_epsg_from_feature(self, feature: fmeobjects.FMEFeature) -> Optional[int]:
              """Try to detect EPSG code from feature coordinate system attributes."""
              try:
                  # Try various coordinate system attribute names
                  coord_sys_attrs = [
                      'coord_sys', 'coordinate_system', 'autocad_coord_sys',
                      'fme_coordinate_system', 'epsg', 'source_epsg'
                  ]

                  for attr in coord_sys_attrs:
                      val = feature.getAttribute(attr)
                      if val:
                          val_str = str(val)
                          # Check if it's a direct EPSG code
                          if val_str.isdigit():
                              return int(val_str)
                          # Check for EPSG: prefix
                          if 'EPSG:' in val_str.upper():
                              epsg_part = val_str.upper().split('EPSG:')[1].split()[0]
                              if epsg_part.isdigit():
                                  return int(epsg_part)
                          # Check for SWEREF names
                          for name, code in _SWEREF_MAP.items():
                              if name.upper() in val_str.upper():
                                  return code
              except Exception as e:
                  print(f"[DWG2Geo] EPSG detection error: {e}")
              return None

          def input(self, feature: fmeobjects.FMEFeature):
              """Collect geometry from each incoming feature."""
              try:
                  # Store first feature for attributes
                  if self._first_feature is None:
                      self._first_feature = feature.clone()
                      self._cfg = config_from_feature(feature)

                      # Get base name from source file
                      source = (feature.getAttribute('fme_basename') or
                                feature.getAttribute('dwg_source_dataset') or
                                feature.getAttribute('autocad_entity_name') or
                                feature.getAttribute('fme_dataset'))
                      if source:
                          self._base_name = os.path.splitext(os.path.basename(str(source)))[0]

                      # Try to detect EPSG from feature
                      detected = self._detect_epsg_from_feature(feature)
                      if detected:
                          self._detected_epsg = detected
                          print(f"[DWG2Geo] Detected EPSG from feature: {detected}")
                          # Update config if not set
                          if self._cfg.source_epsg == 3011 and detected != 3011:
                              self._cfg.source_epsg = detected

                  # Get geometry
                  geom = feature.getGeometry()
                  if geom:
                      # Track bounds for centroid calculation
                      self._update_bounds_from_geometry(geom)

                      # Clone the FEATURE (not geometry) - features always have clone()
                      # We'll extract geometry later when processing
                      self._features.append(feature.clone())

                      # Log geometry type for debugging
                      geom_type = geom.typeName() if hasattr(geom, 'typeName') else type(geom).__name__
                      print(f"[DWG2Geo] Collected geometry #{len(self._features)}: {geom_type}")

              except Exception as e:
                  print(f"[DWG2Geo] Error collecting geometry: {e}")
                  import traceback
                  traceback.print_exc()

          def close(self):
              """Process all collected geometries."""
              if not self._features:
                  print("[DWG2Geo] No geometries collected")
                  return

              print(f"[DWG2Geo] Processing {len(self._features)} collected features")

              # Extract geometries from stored features
              geometries = []
              for feat in self._features:
                  geom = feat.getGeometry()
                  if geom:
                      geometries.append(geom)

              if not geometries:
                  print("[DWG2Geo] No valid geometries found in collected features")
                  return

              print(f"[DWG2Geo] Extracted {len(geometries)} geometries from features")

              # Calculate centroid from bounds if we have valid bounds
              if (self._bounds_min[0] != float('inf') and
                  self._bounds_max[0] != float('-inf')):
                  cx = (self._bounds_min[0] + self._bounds_max[0]) / 2
                  cy = (self._bounds_min[1] + self._bounds_max[1]) / 2
                  cz = 0
                  if self._bounds_min[2] != float('inf'):
                      cz = (self._bounds_min[2] + self._bounds_max[2]) / 2
                  self._centroid = (cx, cy, cz)
                  print(f"[DWG2Geo] Calculated centroid: {self._centroid}")
                  print(f"[DWG2Geo] Bounds: min={self._bounds_min}, max={self._bounds_max}")

                  # Try to compute lat/lon from centroid if not provided
                  if self._cfg.ref_lat is None and self._cfg.ref_lon is None:
                      epsg = self._detected_epsg or self._cfg.source_epsg
                      lat, lon = transform_coords_to_wgs84(cx, cy, epsg)
                      lat, lon = validate_latlon(lat, lon)
                      if lat is not None and lon is not None:
                          self._cfg.ref_lat = lat
                          self._cfg.ref_lon = lon
                          print(f"[DWG2Geo] Computed ref coordinates: lat={lat}, lon={lon}")

              try:
                  result = process_fme_geometries(geometries, self._base_name, self._cfg)

                  # Check if GLB was actually created
                  outputs = result.get('outputs', {})
                  final_glb = outputs.get('final_glb')

                  # Output result feature
                  if self._first_feature:
                      feature = self._first_feature

                      if final_glb and os.path.isfile(final_glb):
                          feature.setAttribute('process_status', 'success')
                          self._success_count += 1
                      else:
                          feature.setAttribute('process_status', 'warning')
                          feature.setAttribute('fme_rejection_message', 'No GLB created - likely no 3D geometry in DWG')
                          print(f"[DWG2Geo] WARNING: No GLB file was created. Check if DWG contains 3D geometry.")

                      feature.setAttribute('warnings', json.dumps(result.get('warnings', [])))
                      feature.setAttribute('final_glb', final_glb or '')
                      feature.setAttribute('plan_geojson', outputs.get('plan_geojson', ''))
                      feature.setAttribute('meta_json', outputs.get('meta_json', ''))
                      feature.setAttribute('geometry_count', len(geometries))

                      feature.setAttribute('lat', result.get('lat'))
                      feature.setAttribute('lon', result.get('lon'))
                      feature.setAttribute('elevation', result.get('elevation', 0))
                      feature.setAttribute('epsg', result.get('epsg'))

                      # Also set centroid and bounds
                      if self._centroid:
                          feature.setAttribute('centroid_x', self._centroid[0])
                          feature.setAttribute('centroid_y', self._centroid[1])
                          feature.setAttribute('centroid_z', self._centroid[2])

                      self._success_count += 1
                      self.pyoutput(feature, output_tag="PYOUTPUT")

              except Exception as e:
                  print(f"[DWG2Geo] Processing error: {e}")
                  import traceback
                  traceback.print_exc()
                  if self._first_feature:
                      self._first_feature.setAttribute("fme_rejection_code", "PROCESSING_ERROR")
                      self._first_feature.setAttribute("fme_rejection_message", str(e))
                      self._first_feature.setAttribute("process_status", "error")
                      self.pyoutput(self._first_feature, output_tag="<Rejected>")
                  self._error_count += 1

              print(f"DWG2Geo Processing complete: {self._success_count} success, {self._error_count} errors")


      # Alias for compatibility with IFC workflow naming
      FeatureProcessor = GeometryProcessor


      # =============================================================================
      # STANDALONE USAGE (for testing outside FME)
      # =============================================================================

      def _run_standalone():
          """Run standalone CLI mode."""
          import argparse

          parser = argparse.ArgumentParser(description='DWG to GLB + GeoJSON pipeline (standalone)')
          parser.add_argument('dwg', help='Path to DWG/DWF file')
          parser.add_argument('--output-dir', '-o', help='Output directory')
          parser.add_argument('--oda-converter', help='Path to ODAFileConverter.exe')
          parser.add_argument('--gltfpack', help='Path to gltfpack executable')
          parser.add_argument('--epsg', type=int, default=3011, help='Source/fallback EPSG code')
          parser.add_argument('--lat', type=float, help='Reference latitude')
          parser.add_argument('--lon', type=float, help='Reference longitude')
          parser.add_argument('--elevation', type=float, default=0, help='Reference elevation')
          args = parser.parse_args()

          cfg = PipelineConfig(
              source_epsg=args.epsg,
              fallback_epsg=args.epsg,
              oda_converter_path=args.oda_converter,
              gltfpack_path=args.gltfpack,
              output_dir=args.output_dir or '',
              ref_lat=args.lat,
              ref_lon=args.lon,
              ref_elevation=args.elevation,
          )

          result = process_dwg_file(args.dwg, cfg)
          print(json.dumps(result, indent=2, default=str))


      if __name__ == '__main__':
          if len(sys.argv) > 1:
              _run_standalone()
    PYTHONSYMBOL = FeatureProcessor

Bookmark: Oom DWG:n inte innhåller 3D-data sparas filen som DXF för att kunna visualiseras i kartan
Layer1 (writer ACAD_2)
    attributes: fme_feature_type_total_count number(20,0)
